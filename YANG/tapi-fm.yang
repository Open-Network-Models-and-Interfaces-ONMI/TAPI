module tapi-fm {
    yang-version "1.1";
    namespace "urn:onf:otcc:yang:tapi-fm";
    prefix tapi-fm;
    import tapi-common {
        prefix tapi-common;
    }
    import tapi-notification {
        prefix tapi-notification;
    }
    import tapi-streaming {
        prefix tapi-streaming;
    }
    organization "Linux Foundation ONMI (Open Network Modeling and Interfaces) Project";
    contact "
         Project Web: <https://github.com/Open-Network-Models-and-Interfaces-ONMI/onmi-home/wiki>
         Project List: <mailto:onmi-tapi@googlegroups.com>
         Editor: Nigel Davis <mailto:ndavis@ciena.com>
         Arturo Mayoral <mailto:amayoral@telecominfraproject.com>
         Ramon Casellas <mailto:ramon.casellas@cttc.es>";
    description "
        This module contains TAPI Fault Management Model definitions.
        Source: TapiFm.uml
        - The TAPI YANG models included in this TAPI release are a *normative* part of the TAPI SDK.
        - The YANG specifications have been generated from the corresponding UML model using the [EAGLE UML2YANG mapping tool]
        <https://github.com/Open-Network-Models-and-Interfaces-ONMI/onmi-iisomi-uml-yang>
        and further edited manually to comply with the [ONMI IISOMI UML2YANG mapping guidelines]
        <https://github.com/Open-Network-Models-and-Interfaces-ONMI/onmi-iisomi-home>
        - Status of YANG model artifacts can be determined by referring to the corresponding UML artifacts.
        As described in the UML models, some artifacts are considered *experimental*, and thus the corresponding YANG artifacts.
        - The LF ONMI TAPI release process does not guarantee backward compatibility of YANG models across major versions of TAPI releases.
        The YANG model backward compatibility criteria are outlined in section 11 of <https://tools.ietf.org/html/rfc7950>.
        YANG models included in this release may not be backward compatible with some previous TAPI releases.
        - Previous revisions can now be found at https://github.com/Open-Network-Models-and-Interfaces-ONMI/TAPI under the 
        appropriate tag and, where relevant, fixes to those revisions can be found under the corresponding branches. The documentation for
        each significant revision is found at https://github.com/Open-Network-Models-and-Interfaces-ONMI/TAPI-Documentation under the
        appropriate tag and, where relevant, fixes to those revisions can be found under the corresponding branches.
        License: This module is distributed under the Apache License 2.0.";
    revision 2025-12-31 {
        description "LF ONMI Transport API version 2.5.2
                   Changes included in this TAPI release (v2.5.2) are listed in
                   <https://github.com/Open-Network-Models-and-Interfaces-ONMI/TAPI-Documentation/tree/v2.5.2/DeltaDocument>";
        reference "ONF-TR-527, ONF-TR-512, ONF-TR-531, RFC 7950, RFC 6087 and LF ONMI TAPI UML model
                  <https://github.com/Open-Network-Models-and-Interfaces-ONMI/TAPI/tree/v2.5.2/UML>";
    }
    revision 2023-10-10 {
        description "ONF Transport API version 2.5.0.
                   Changes included in this TAPI release (v2.5.0) are listed in
                   <https://wiki.opennetworking.org/display/OTCC/TAPI+Roadmap+2023>";
        reference "ONF-TR-527, ONF-TR-512, ONF-TR-531, RFC 7950, RFC 6087 and ONF TAPI UML model
                  <https://github.com/OpenNetworkingFoundation/TAPI/tree/v2.5.0/UML>";
    }
    revision 2023-03-21 {
        description "ONF Transport API version 2.4.1.
                   Changes included in this TAPI release (v2.4.1) are listed in
                   <https://wiki.opennetworking.org/display/OTCC/TAPI+Roadmap+2023>";
        reference "ONF-TR-527, ONF-TR-512, ONF-TR-531, RFC 7950, RFC 6087 and ONF TAPI UML model
                  <https://github.com/OpenNetworkingFoundation/TAPI/tree/v2.4.1/UML>";
    }
    revision 2022-12-22 {
        description "ONF Transport API version 2.4.0.
                   Changes included in this TAPI release (v2.4.0) are listed in
                   <https://wiki.opennetworking.org/display/OTCC/TAPI+Roadmap+2023>";
        reference "ONF-TR-527, ONF-TR-512, ONF-TR-531, RFC 7950, RFC 6087 and ONF TAPI UML model
                  <https://github.com/OpenNetworkingFoundation/TAPI/tree/v2.4.0/UML>";
    }
    revision 2022-11-21 {
        description "ONF Transport API version 2.4.0 RC1.
                   Changes included in this TAPI release (v2.4.0) are listed in
                   <https://wiki.opennetworking.org/display/OTCC/TAPI+Roadmap+2023>";
        reference "ONF-TR-527, ONF-TR-512, ONF-TR-531, RFC 7950, RFC 6087 and ONF TAPI UML model
                  <https://github.com/OpenNetworkingFoundation/TAPI/tree/v2.4.0-RC1/UML>";
    }
    revision 2021-09-24 {
        description "ONF Transport API version 2.3.1.
                   Changes included in this TAPI release (v2.3.1) are listed in
                   <https://wiki.opennetworking.org/display/OTCC/Archived+Deliveries>";
        reference "ONF-TR-527, ONF-TR-512, ONF-TR-531, RFC 7950, RFC 6087 and ONF TAPI UML model
                  <https://github.com/OpenNetworkingFoundation/TAPI/tree/v2.3.1/UML>";
    }
    revision 2021-08-04 {
        description "ONF Transport API version 2.3.
                   Changes included in this TAPI release (v2.3) are listed in
                   <https://wiki.opennetworking.org/display/OTCC/Archived+Deliveries>";
        reference "ONF-TR-527, ONF-TR-512, ONF-TR-531, RFC 7950, RFC 6087 and ONF TAPI UML model
                  <https://github.com/OpenNetworkingFoundation/TAPI/tree/v2.3/UML>";
    }
    revision 2021-05-24 {
        description "ONF Transport API version 2.3 RC1.
                   Changes included in this TAPI release (v2.3) are listed in
                   <https://wiki.opennetworking.org/display/OTCC/Archived+Deliveries>";
        reference "ONF-TR-527, ONF-TR-512, ONF-TR-531, RFC 7950, RFC 6087 and ONF TAPI UML model
                  <https://github.com/OpenNetworkingFoundation/TAPI/tree/v2.3/UML>";
    }
    revision 2020-04-23 {
        description "ONF Transport API version 2.1.3.
                   Changes included in this TAPI release (v2.1.3) are listed in
                   <https://github.com/OpenNetworkingFoundation/TAPI/blob/develop_v2_1/CHANGE_LOG/change-log.2.1.3.md>";
        reference "ONF-TR-527, ONF-TR-512, ONF-TR-531, RFC 7950, RFC 6087 and ONF TAPI UML model
                  <https://github.com/OpenNetworkingFoundation/TAPI/tree/v2.1.3/UML>";
    }
    revision 2019-07-16 {
        description "ONF Transport API version 2.1.2.
                   Changes included in this TAPI release (v2.1.2) are listed in
                   <https://github.com/OpenNetworkingFoundation/TAPI/blob/develop_v2_1/CHANGE_LOG/change-log.2.1.2.md>";
        reference "ONF-TR-527, ONF-TR-512, ONF-TR-531, RFC 7950, RFC 6087 and ONF TAPI UML model
                  <https://github.com/OpenNetworkingFoundation/TAPI/tree/v2.1.2/UML>";
    }
    revision 2019-03-31 {
        description "ONF Transport API version 2.2-RC1.
                   Changes included in this TAPI release (v2.2) are listed in
                  <https://github.com/OpenNetworkingFoundation/TAPI/blob/develop/CHANGE_LOG/change-log.2.2.md>";
        reference "ONF-TR-527, ONF-TR-512, ONF-TR-531, RFC 7950, RFC 6087 and ONF TAPI UML model
                  <https://github.com/OpenNetworkingFoundation/TAPI/tree/v2.2.0/UML>";
    }
    revision 2018-12-10 {
        description "ONF Transport API version 2.1.1.
                   Changes included in this TAPI release (v2.1.1) are listed in
                  <https://github.com/OpenNetworkingFoundation/TAPI/blob/develop/CHANGE_LOG/change-log.2.1.1.md>";
        reference "ONF-TR-527, ONF-TR-512, ONF-TR-531, RFC 7950, RFC 6087 and ONF TAPI UML model
                  <https://github.com/OpenNetworkingFoundation/TAPI/tree/v2.1.1/UML>";
    }
    revision 2018-10-16 {
        description "ONF Transport API version 2.1.0.
                   Changes included in this TAPI release (v2.1.0) are listed in
                  <https://github.com/OpenNetworkingFoundation/TAPI/blob/develop/CHANGE_LOG/change-log.2.1.0.md>";
        reference "ONF-TR-527, ONF-TR-512, ONF-TR-531, RFC 7950, RFC 6087 and ONF TAPI UML model
                  <https://github.com/OpenNetworkingFoundation/TAPI/tree/v2.1.0/UML>";
    }
    revision 2018-03-07 {
        description "ONF Transport API version 2.0.2
        This YANG module has been generated from the TAPI UML Model using the IISOMI-Eagle xmi2yang mapping tool.
        Changes in this revision: <https://github.com/OpenNetworkingFoundation/TAPI/blob/develop/CHANGE_LOG/change-log.2.0.2.md>";
        reference "ONF-TR-527, ONF-TR-512, ONF-TR-531, RFC 6020, RFC 6087 and ONF TAPI UML model
                  <https://github.com/OpenNetworkingFoundation/TAPI/tree/v2.0.2/UML>";
    }
    revision 2018-02-16 {
        description "ONF Transport API version 2.0.1
        This YANG module has been generated from the TAPI UML Model using the IISOMI-Eagle xmi2yang mapping tool.
        Changes in this revision: <https://github.com/OpenNetworkingFoundation/TAPI/blob/develop/CHANGE_LOG/change-log.2.0.1.md>";
        reference "ONF-TR-527, ONF-TR-512, ONF-TR-531, RFC 6020, RFC 6087 and ONF TAPI UML model
                  <https://github.com/OpenNetworkingFoundation/TAPI/tree/v2.0.1/UML>";
    }
    revision 2018-01-02 {
        description "ONF Transport API version 2.0.0
        This YANG module has been generated from the TAPI UML Model using the IISOMI-Eagle xmi2yang mapping tool.
        Changes in this revision: <https://github.com/OpenNetworkingFoundation/TAPI/blob/develop/CHANGE_LOG/change-log.2.0.0.md>";
        reference "ONF-TR-527, ONF-TR-512, ONF-TR-531, RFC 6020, RFC 6087 and ONF TAPI UML model
                  <https://github.com/OpenNetworkingFoundation/TAPI/tree/v2.0.0/UML>";
    }
    augment "/tapi-common:context/tapi-notification:notification-context/tapi-notification:notification" {
        container alarm-info {
            uses alarm-info;
            description "none";
        }
        description "none";
    }
    augment "/tapi-common:context/tapi-notification:notification-context/tapi-notification:event-notification" {
        container detected-condition {
            uses detected-condition;
            description "none";
        }
        description "none";
    }
    augment "/tapi-common:context/tapi-notification:notification-context/tapi-notification:notification" {
        container tca-info {
            uses tca-info;
            description "none";
        }
        description "none";
    }
    augment "/tapi-streaming:stream-record/tapi-streaming:log-record/tapi-streaming:log-record-body/tapi-streaming:condition-detector" {
        container detected-condition {
            uses detected-condition;
            description "none";
        }
        description "none";
    }
    augment "/tapi-notification:notification" {
        container alarm-info {
            uses alarm-info;
            description "none";
        }
        description "none";
    }
    augment "/tapi-notification:event-notification" {
        container detected-condition {
            uses detected-condition;
            description "none";
        }
        description "none";
    }
    augment "/tapi-notification:notification" {
        container tca-info {
            uses tca-info;
            description "none";
        }
        description "none";
    }
    augment "/tapi-common:context/tapi-fm:fault-management-context/tapi-fm:active-condition" {
        container detected-condition {
            uses detected-condition;
            description "none";
        }
        description "none";
    }
    augment "/tapi-common:context" {
        container fault-management-context {
            uses fault-management-context;
            description "Augments the base TAPI Context with FaultManagementContext model.";
        }
        description "Augments the base TAPI Context with FaultManagementContext model.";
    }
    /**************************
    * package object-classes
    **************************/ 
    grouping alarm-info {
        leaf alarm-name {
            type tapi-common:alr;
            config false;
            description "The probable cause of the failure (detected fault).
                G.806:
                - fault: A fault is the inability of a function to perform a required action. This does not include an inability due to preventive maintenance, lack of external resources or planned actions.
                - fault cause: A single disturbance or fault may lead to the detection of multiple defects.
                - defect: The density of anomalies has reached a level where the ability to perform a required function has been interrupted.
                Defects are used as input for performance monitoring, the control of consequent actions and for the determination of fault causes.
                A fault cause is the result of a correlation process which is intended to identify the defect that is representative of the disturbance or fault that is causing the problem.
                - failure: The fault cause persisted long enough to consider the ability of an item to perform a required function to be terminated. The item may be considered as failed; a fault has now been detected.
                - alarm: A human-observable indication that draws attention to a failure (detected fault) usually giving an indication of the severity of the fault.";
        }
        leaf native-alarm-name {
            type string;
            config false;
            description "The probable cause of the failure as shown by lower level controllers.";
        }
        leaf native-alarm-info {
            type string;
            config false;
            description "Additional info made available by the lower level controllers.";
        }
        leaf is-transient {
            type boolean;
            config false;
            description "An alarm is transient when stateless, i.e. an explicit clear notification is not foreseen.";
        }
        leaf perceived-severity {
            type perceived-severity-type;
            config false;
            description "The alarm severity.";
        }
        leaf service-affecting {
            type service-affecting;
            config false;
            description "The impact on the service.";
        }
        leaf alarm-category {
            type alarm-category;
            config false;
            description "The alarm category, based on ITU-T X.733.";
        }
        leaf alarm-qualifier {
            type string;
            config false;
            description "Further information necessary to precisely/uniquely/unambiguously identify the alarm detector.
                For Equipment and Processing Alarm Category, e.g. the local id of the ActualNonFieldReplaceableModule which identifies exact alarm source.
                For Environment Alarm Category, e.g. on the same Device instance may appear more Environmental alarm notifications with same Alarn Name.
                For Connectivity Alarm Category in case that same CEP instance includes e.g. both OTS and OMS monitoring layers.";
        }
        description "This class augments the Notification class with alarm related parameters.
            This class is deprecated in favor of DetectedCondition class, which unifies alarm and TCA related parameters.";
    }
    grouping tca-info {
        leaf threshold-indicator-name {
            type tapi-common:pm;
            config false;
            description "PM metric name which TCA refers to.";
        }
        leaf native-threshold-indicator-name {
            type string;
            config false;
            description "PM metric name which TCA refers to as shown by lower level controllers.";
        }
        leaf native-tca-info {
            type string;
            config false;
            description "Additional info made available by the lower level controllers.";
        }
        leaf is-transient {
            type boolean;
            config false;
            description "A threshold crossing alert is transient when stateless, i.e. an explicit clear notification is not foreseen.";
        }
        leaf perceived-tca-severity {
            type perceived-tca-severity;
            config false;
            description "The threshold crossing alert severity.";
        }
        container threshold-observed-value {
            config false;
            uses tapi-common:pm-parameter-value;
            description "The observed value of PM metric to which TCA refers to.";
        }
        container threshold-configured-value {
            config false;
            uses tapi-common:pm-parameter-value;
            description "The configured threshold value of PM metric to which TCA refers to.";
        }
        leaf oam-job {
            type tapi-common:uuid;
            config false;
            description "Reference to the OamJob instance for which the PM metric and threshold values were configured.
                The reference is defined as simple UUID because TapiFm does not import TapiOam.
                MEF 35.1: Identification of the PM Session for which the TCA Function was configured.";
        }
        leaf tca-qualifier {
            type string;
            config false;
            description "Further information necessary to precisely/uniquely/unambiguously identify the TCA detector.";
        }
        container granularity-period {
            config false;
            uses tapi-common:time-period;
            description "The granularity period or measurement interval time.
                This parameter may be necessary when the reference to the OAM Job is not included, e.g. in case the OAM job is not visible at the management interface.";
        }
        leaf tca-category {
            type alarm-category;
            config false;
            description "The TCA category, based on ITU-T X.733.";
        }
        description "This class augments the Notification class with threshold crossing alert related parameters.
            This class is deprecated in favor of DetectedCondition class, which unifies alarm and TCA related parameters.";
    }
    grouping detected-condition {
        leaf detected-condition-name {
            type tapi-common:dc;
            config false;
            description "The name of the Condition, e.g. an alarm probable cause or the PM metric name which threshold crossing alert refers to.
                ITU-T probable cause of the failure (detected fault).
                G.806:
                - fault: A fault is the inability of a function to perform a required action. This does not include an inability due to preventive maintenance, lack of external resources or planned actions.
                - fault cause: A single disturbance or fault may lead to the detection of multiple defects.
                - defect: The density of anomalies has reached a level where the ability to perform a required function has been interrupted.
                Defects are used as input for performance monitoring, the control of consequent actions and for the determination of fault causes.
                A fault cause is the result of a correlation process which is intended to identify the defect that is representative of the disturbance or fault that is causing the problem.
                - failure: The fault cause persisted long enough to consider the ability of an item to perform a required function to be terminated. The item may be considered as failed; a fault has now been detected.
                - alarm: A human-observable indication that draws attention to a failure (detected fault) usually giving an indication of the severity of the fault.";
        }
        leaf detected-condition-native-name {
            type string;
            config false;
            description "The name used for the Condition by the source of the information.";
        }
        leaf detected-condition-native-info {
            type string;
            config false;
            description "Additional info of the Condition provided by the source of the information.";
        }
        leaf detected-condition-qualifier {
            type string;
            config false;
            description "Further information necessary to precisely/uniquely/unambiguously identify the Condition Detector.
                For Equipment and Processing Alarm Category, e.g. the local id of the ActualNonFieldReplaceableModule which identifies exact alarm source.
                For Environment Alarm Category, e.g. on the same Device instance may appear more Environmental alarm notifications with same Alarn Name.
                For Connectivity Alarm Category in case that same CEP instance includes e.g. both OTS and OMS monitoring layers.";
        }
        leaf oam-job {
            type tapi-common:uuid;
            config false;
            description "Reference to the OamJob instance for which the Condition detection has been configured, e.g. configuration of PM metrics and threshold values and/or of the (alarm) Conditions.
                The reference is defined as simple UUID because TapiFm does not import TapiOam.
                MEF 35.1: Identification of the PM Session for which the TCA Function was configured.";
        }
        container pm-metric-info {
            config false;
            uses pm-metric-info;
            description "The PM metric information.";
        }
        container detector-info {
            config false;
            uses detector-info;
            description "The detector info for alarm and TCA.";
        }
        container simple-detector {
            config false;
            uses simple-detector;
            description "The simple detector state.";
        }
        description "A record of the state of a Detector where that Detector has two underling states that are of asymmetric importance.
            For example, an alarm or a threshold crossing alert detected on a given resource.
            A Condition Detector represents any monitoring component that assesses properties of something and determines from those properties what conditions are associated with the thing.
            For example, a thing might be 'too hot' or might be 'unreliable'.";
    }
    grouping detector-info {
        leaf perceived-severity {
            type perceived-severity-type;
            config false;
            description "The severity of the detected Condition.";
        }
        leaf service-affecting {
            type service-affecting;
            config false;
            description "The impact on the service.";
        }
        leaf is-acknowledge {
            type boolean;
            config false;
            description "Information on operator acknowledgement.";
        }
        leaf detector-category {
            type detector-category;
            config false;
            description "The Detector (alarm) category, based on ITU-T X.733.";
        }
        description "(Legacy) information associated to a Condition (alarm).";
    }
    grouping simple-detector {
        leaf simple-detector-state {
            type simple-detector-state;
            config false;
            description "The (simple) state of the Detector.
                The Detector state accounts for the time characteristics of the detected Condition.";
        }
        description "Information regarding the (simple) state of the Detector.";
    }
    grouping pm-metric-info {
        container threshold-observed-value {
            config false;
            uses tapi-common:pm-parameter-value;
            description "The observed value of PM metric to which TCA refers to.";
        }
        container threshold-configured-value {
            config false;
            uses tapi-common:pm-parameter-value;
            description "The configured threshold value of PM metric to which TCA refers to.";
        }
        container granularity-period {
            config false;
            uses tapi-common:time-period;
            description "The granularity period or measurement interval time.
                This parameter may be necessary when the reference to the OAM Job is not included, e.g. in case the OAM job is not visible at the management interface.";
        }
        description "Information associated to a Threshold Crossing Alert.";
    }
    grouping active-condition {
        leaf target-object-type {
            type tapi-common:object-type;
            config false;
            description "The ActiveCondition instance is related to the object instance (of a global class - with UUID) with this ObjectType value.
                Alternatively, the ActiveCondition is related to the object instance of a local class, whose global object has this ObjectType value.";
        }
        leaf target-object-identifier {
            type tapi-common:uuid;
            config false;
            description "The ActiveCondition instance is related to the object instance (of a global class) with this UUID value.
                Alternatively, the ActiveCondition is related to the object instance of a local class, whose global object has this UUID value.";
        }
        leaf target-local-object-type {
            type tapi-common:object-type;
            config false;
            description "The ActiveCondition instance is related to the object instance of a local class, whose global object has targetObjectType value.";
        }
        leaf target-local-object-identifier {
            type string;
            config false;
            description "The ActiveCondition instance is related to the object instance of a local class, whose global object has targetObjectIdentifier value.";
        }
        leaf target-object-dri {
            type string;
            config false;
            description "Data Resource Identifier of the target object as per RFC 8040.";
        }
        list target-object-name {
            key 'value-name';
            config false;
            uses tapi-common:name-and-value;
            description "The ActiveCondition instance is related to the object instance with this list of names.";
        }
        leaf layer-protocol-name {
            type tapi-common:layer-protocol-name;
            config false;
            description "The ActiveCondition instance is related to a resource with this layer protocol value.";
        }
        leaf-list layer-protocol-qualifier {
            type tapi-common:layer-protocol-qualifier;
            config false;
            description "The ActiveCondition instance is related to a resource with these layer protocol qualifier values.";
        }
        leaf event-time-stamp {
            type tapi-common:date-and-time;
            config false;
            description "The best knowledge of the time of the event which originated this ActiveCondition instance.";
        }
        leaf source-indicator {
            type tapi-notification:source-indicator;
            config false;
            description "The possible source of this ActiveCondition instance.";
        }
        list additional-info {
            key 'value-name';
            config false;
            uses tapi-common:name-and-value;
            description "none";
        }
        uses tapi-common:global-class;
        description "This object describes the current active condition (alarm or TCA) of the target object.";
    }
    grouping fault-management-context {
        list active-condition {
            key 'uuid';
            config false;
            uses active-condition;
            description "none";
        }
        description "This object class represents the scope of control that a particular SDN controller has with respect to a particular network, specifically regarding the fault management description.
            An instance of this class includes its ActiveCondition instances.";
    }

    /**************************
    * package type-definitions
    **************************/ 
    identity ALARM_CATEGORY {
        description "none";
    }
    identity ALARM_CATEGORY_EQUIPMENT {
        base ALARM_CATEGORY;
        description "none";
    }
    identity ALARM_CATEGORY_ENVIRONMENT {
        base ALARM_CATEGORY;
        description "none";
    }
    identity ALARM_CATEGORY_CONNECTIVITY {
        base ALARM_CATEGORY;
        description "none";
    }
    identity ALARM_CATEGORY_PROCESSING {
        base ALARM_CATEGORY;
        description "none";
    }
    identity ALARM_CATEGORY_SECURITY {
        base ALARM_CATEGORY;
        description "none";
    }
    identity PERCEIVED_TCA_SEVERITY {
        description "none";
    }
    identity PERCEIVED_TCA_SEVERITY_WARNING {
        base PERCEIVED_TCA_SEVERITY;
        description "ITU-T G.7710/X.733/M.3100: Indication for a potential or impending service-affecting fault. Further diagnosis should be made.";
    }
    identity PERCEIVED_TCA_SEVERITY_CLEAR {
        base PERCEIVED_TCA_SEVERITY;
        description "Included only for some possible backward compatibility purpose. It should not be used to assign a severity to a failure.
            ITU-T G.7710: The severities 'cleared' and 'indeterminate' defined by [ITU-T X.733] are not included in Table 2, as it is assumed that these are not to be used to assign a failure.";
    }
    identity FM {
        base tapi-notification:NOTIFICATION_TYPE;
        description "none";
    }
    identity FM_ALARM_EVENT {
        base FM;
        description "The notification of a detected condition event, specifically an alarm detected on a given resource.";
    }
    identity FM_THRESHOLD_CROSSING_ALERT {
        base FM;
        description "The notification of a detected condition event, specifically a threshold crossing alert detected on a given resource.";
    }
    identity CONDITION_TYPE {
        description "none";
    }
    identity CONDITION_TYPE_ALARM {
        base CONDITION_TYPE;
        description "none";
    }
    identity CONDITION_TYPE_TCA {
        base CONDITION_TYPE;
        description "Threshold Crossing Alert";
    }
    identity DETECTOR_CATEGORY {
        description "none";
    }
    identity DETECTOR_CATEGORY_EQUIPMENT {
        base DETECTOR_CATEGORY;
        description "none";
    }
    identity DETECTOR_CATEGORY_ENVIRONMENT {
        base DETECTOR_CATEGORY;
        description "none";
    }
    identity DETECTOR_CATEGORY_CONNECTIVITY {
        base DETECTOR_CATEGORY;
        description "none";
    }
    identity DETECTOR_CATEGORY_PROCESSING {
        base DETECTOR_CATEGORY;
        description "none";
    }
    identity DETECTOR_CATEGORY_SECURITY {
        base DETECTOR_CATEGORY;
        description "none";
    }
    identity DETECTOR_CATEGORY_UNDEFINED {
        base DETECTOR_CATEGORY;
        description "none";
    }
    identity SIMPLE_DETECTOR_STATE {
        description "none";
    }
    identity SIMPLE_DETECTOR_STATE_ACTIVE {
        base SIMPLE_DETECTOR_STATE;
        description "The detector is indicating the operation of the monitored entity is not within acceptable bounds with respect to the specific condition measured.
            If INTERMITTENT is supported there may be a requirement for persisted unacceptable operation after a problem occurs before ACTIVE is declared. An alternative may be to declare INTERMITTENT.
            Where INTERMITTENT is supported, ACTIVE indicates the stable presence of a problem.";
    }
    identity SIMPLE_DETECTOR_STATE_CLEAR {
        base SIMPLE_DETECTOR_STATE;
        description "The detector is indicating the operation of the monitored entity is within acceptable bounds with respect to the specific condition measured.";
    }
    identity SIMPLE_DETECTOR_STATE_INTERMITTENT {
        base SIMPLE_DETECTOR_STATE;
        description "The detector is indicating the operation of the monitored entity is intermittently not within acceptable bounds with respect to the specific condition measured.
            INTERMITTENT support is optional. Where it is supported there may be a requirement for persisted unacceptable operation after a problem occurs before ACTIVE or INTERMITTENT is declared.";
    }
    identity SIMPLE_DETECTOR_STATE_FLEETING {
        base SIMPLE_DETECTOR_STATE;
        description "Event has a very short life (Active-Clear), hence is notified/streamed after its occurrence.";
    }
    identity SIMPLE_DETECTOR_STATE_ACTIVE_NO_EXPLICIT_CLEAR {
        base SIMPLE_DETECTOR_STATE;
        description "Same as Active, but an explicit transition to Clear is not foreseen.
            This e.g. applies to PM metrics which can only increase (counters), hence the 'clear' criteria is conventionally the end of a measurement period.";
    }
    typedef alarm-category {
        type identityref {
            base ALARM_CATEGORY;
        }
        description "none";
    }
    typedef perceived-severity-type {
        type enumeration {
            enum CRITICAL {
                description "ITU-T G.7710/X.733/M.3100: Indication for a service-affecting condition. Immediate corrective action is required.";
            }
            enum MAJOR {
                description "ITU-T G.7710/X.733/M.3100: Indication for a service-affecting condition. Urgent corrective action is required.";
            }
            enum MINOR {
                description "ITU-T G.7710/X.733/M.3100: Indication for a non-service-affecting condition. Corrective action should be taken in order to prevent more serious fault.";
            }
            enum WARNING {
                description "ITU-T G.7710/X.733/M.3100: Indication for a potential or impending service-affecting fault. Further diagnosis should be made.";
            }
            enum CLEARED {
                description "Included only for some possible backward compatibility purpose. It should not be used to assign a severity to a failure.
                    ITU-T G.7710: The severities 'cleared' and 'indeterminate' defined by [ITU-T X.733] are not included in Table 2, as it is assumed that these are not to be used to assign a failure.";
            }
        }
        description "The types of perceived severity.
            ITU-T G.7710: Failures may have been categorized to indicate the severity or urgency of the fault.";
    }
    typedef service-affecting {
        type enumeration {
            enum SERVICE_AFFECTING {
                description "The service is affected by the detected Condition.";
            }
            enum NOT_SERVICE_AFFECTING {
                description "The service is not affected by the detected Condition.";
            }
            enum UNKNOWN {
                description "The impact on the service is unknown.";
            }
        }
        description "The possible impact on the service.";
    }
    typedef perceived-tca-severity {
        type identityref {
            base PERCEIVED_TCA_SEVERITY;
        }
        description "The types of perceived severity of threshold crossing alerts.";
    }
    typedef fm {
        type identityref {
            base FM;
        }
        description "The list of alarm specific notification types.";
    }
    typedef condition-type {
        type identityref {
            base CONDITION_TYPE;
        }
        description "The types of the Condition.";
    }
    typedef detector-category {
        type identityref {
            base DETECTOR_CATEGORY;
        }
        description "The Detector (alarm) category, based on ITU-T X.733.";
    }
    typedef simple-detector-state {
        type identityref {
            base SIMPLE_DETECTOR_STATE;
        }
        description "The states of the detector.";
    }

}
