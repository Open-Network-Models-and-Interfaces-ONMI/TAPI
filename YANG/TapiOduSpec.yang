module TapiOduSpec {
    namespace "urn:onf:params:xml:ns:yang:TapiOduSpec";
    prefix TapiOduSpec;
    import Tapi {
        prefix Tapi;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-29 {
        description "Latest revision";
        reference "RFC 6020 and RFC 6087";
    }
    /***********************
    * package ObjectClasses
    **********************/ 
        grouping OduAdapterAndConnectionPointSpec {
            leaf adaptationActive {
                type boolean;
                config false;
                description "This attribute is applicable when the ODUk CTP object instance represents a lower order ODUk at the ODUkP/ODU[i]j or ODUkP/ODUj-21 adaptation function. This attribute indicates whether the adaptation function is activated or not. Valid values are true and false. The value of true means that the adaptation function shall access the access point when it is activated (MI_Active is true). Otherwise, it shall not access the access point.";
            }
            leaf apsEnable {
                type boolean;
                default "true";
                description "This attribute is for enabling/disabling the automatic protection switching (APS) capability at the transport adaptation function that is represented by the ODUk_ConnectionTerminationPoint object class. It triggers the MI_APS_EN signal to the transport adaptation function.";
            }
            leaf apsLevel {
                type uint64;
                description "This attribute is for configuring the automatic protection switching (APS) level that should operate at the transport adaptation function that is represented by the ODUk_ConnectionTerminationPoint object class. It triggers the MI_APS_LVL signal to the transport adaptation function. The value 0 means path and the values 1 through 6 mean TCM level 1 through 6 respectively.";
            }
            leaf k {
                type ODUk_CtpKBitRate;
                config false;
                description "This attribute specifies the index k that is used to represent a supported bit rate and the different versions of OPUk, ODUk and OTUk.
                    When the ODU CTP is an instance of lower order ODU of a higher order ODU at the ODUkP/ODU[i]j adaptation function, valid values for the index and number of allowed instances of this object class are limited as specified in Table 14-27/G.798.  The restriction is basically HO index k=1, 2, 3 and LO j=0, 1, 2 with j less than k and optionally i=1 with i less than j.
                    When the ODU CTP is an instance of lower order ODU of a higher order ODU at the client layer of the ODUkP/ODUj-21_A adaptation function, valid values for the index of this object class is limited by the rule HO index k=2, 3, 4 and LO j=0, 1, 2, 2e, 3, flex with j less than k.
                    ";
            }
            leaf oduTypeAndRate {
                type uint64;
                description "This attribute is applicable when the ODUk CTP object instance represents a lower order ODUk CTP Source or Sink at the client layer of the ODUkP/ODUj-21 adaptation function. The value of this attribute specifies the type and rate of the adaptation and thus can be used to determine, according to Table 7-10/G.709, the mapping method and, in the case of GMP mapping, the base value and ranges for the parameters Cn and Cm. The value of this attribute is a triplet {j, k, size}, where j = 0, 1, 2, 2e, 3, flex; for the rate of the client ODUj  k = 1, 2, 3, 4; for the rate of the server ODUk size = 1.25G, 2.5G";
            }
            leaf-list positionSeq {
                type ODUk_TcmOrGccChoice;
                config false;
                description "This attribute indicates the positions of the TCM and GCC processing functions within the ODUk TP.
                    The order of the position in the positionSeq attribute together with the signal flow determine the processing sequence of the TCM and GCC functions within the ODUk TP. Once the positions are determined, the signal processing sequence will follow the signal flow for each direction of the signal.
                    Within the ODUk_CTP, the position order is going from adaptation to connection function. Within the ODUk_TTP, the order is going from connection to adaptation function.
                    The syntax of the PositionSeq attribute will be a SEQUENCE OF pointers, which point to the contained TCM and GCC function.
                    The order of TCM and GCC access function in the positionSeq attribute is significant only when there are more than one TCM functions within the ODUk TP and also at least one of them have the TimActDisabled attribute set to FALSE (i.e. AIS is inserted upon TIM).
                    If a GCC12_TP is contained in an ODUk_TTP and the GCC12_TP is not listed in the PositionSeq attribute of the ODUk_TTP, then the GCC access is at the AP side of the ODUk TT function.
                    ";
            }
            leaf-list tcmFieldsInUse {
                type uint64;
                config false;
                description "This attribute indicates the used TCM fields of the ODUk OH.";
            }
            leaf-list tributarySlotList {
                type uint64;
                config false;
                min-elements 1;
                description "This attribute contains a set of distinct (i.e. unique) integers (e.g. 2, 3, 5, 9, 15 representing the tributary slots TS2, TS3, TS5, TS9 and TS15) which represents the resources occupied by the Low Order ODUk Link Connection (e.g. carrying an ODUflex with a bit rate of 6.25G). This attribute applies when the LO ODUk_ ConnectionTerminationPoint connects with an HO ODUk_TrailTerminationPoint object. It will not apply if this ODUk_ ConnectionTerminationPoint object directly connects to an OTUk_TrailTerminationPoint object (i.e. OTUk has no trib slots). The upper bound of the integer allowed in this set is a function of the HO-ODUk server layer to which the ODUk connection has been mapped (adapted). Thus, for example, M=8/32/80 for ODU2/ODU3/ODU4 server layers (respectively). Note that the value of this attribute can be changed only in the case of ODUflex and has to be through specific operations (i.e. not be changing the attribute tributarySlotList directly).";
            }
            leaf applicableProblems {
                type ODUk_CtpProblemList;
                config false;
                description "This attribute's datatype indicates the potential failure conditions of the entity.   The values are to be used in the inherited currentProblemList.";
            }
            leaf expectedMSI {
                type string;
                description "This attribute is applicable when the ODUk CTP object instance represents a lower order ODU1 or ODU2 CTP Sink at the client layer of the ODU3P/ODU12 adaptation function or represents a lower order ODUj CTP Sink at the client layer of the ODUkP/ODUj-21 adaptation function. This attribute is a 1-byte field that configures the expected multiplex structure of the adaptation function. ";
            }
            leaf acceptedMSI {
                type string;
                config false;
                description "This attribute is applicable when the ODUk CTP object instance represents a lower order ODU1 or ODU2 CTP Sink at the client layer of the ODU3P/ODU12 adaptation function or represents a lower order ODUj CTP Sink at the client layer of the ODUkP/ODUj-21 adaptation function. This attribute is a 1-byte field that represents the accepted multiplex structure of the adaptation function. ";
            }
            leaf acceptedPayloadType {
                type string;
                config false;
                description "This attribute is applicable when the ODUk CTP object instance represents a lower order ODUk CTP Sink at the client layer of the ODUkP/ODU[i]j or ODUkP/ODUj-21 adaptation function. This attribute is a 2-digit Hex code that indicates the new accepted payload type. ";
            }
            leaf transmittedMSI {
                type string;
                description "This attribute is applicable when the ODUk CTP object instance represents a lower order ODU1 or ODU2 CTP Source at the client layer of the ODU3P/ODU12 adaptation function, or a lower order ODUj CTP Source at the client layer of the ODUkP/ODUj-21 adaptation function. This attribute is a 1-byte field that configures the transmitted multiplex structure identifier of the adaptation function.";
            }
            leaf autoPayloadType {
                type boolean;
                description "This attribute is applicable when the ODUk CTP object instance represents a lower order ODU CTP Source at the client layer of the ODUkP/ODUj-21 adaptation function. The value of true of this attribute configures that the adaptation source function shall fall back to the payload type PT=20 if the conditions specified in 14.3.10.1/G.798 are satisfied. ";
            }
            leaf insertedPayloadType {
                type string;
                config false;
                description "This attribute is applicable when the ODUk CTP object instance represents a lower order ODU CTP Source at the client layer of the ODUkP/ODUj-21 adaptation function. The attribute reports the inserted payload type (i.e. TrPT) for the PT byte position of the PSI overhead. Valid values for this attribute are 20 and 21. For more details see 14.3.10.1/G.798. ";
            }
            leaf-list currentNumberOfTributarySlots {
                type uint64;
                config false;
                min-elements 1;
                description "This attribute applies only to ODUflex(GFP) connections. It represents the current number of tributary slots allocated to this ODUflex(GFP) connection in the HO-ODU server layer. The value of this parameter determines the bit rate of the ODUflex connection. 
                    The upper bound of this attribute is dependent on the HO-ODUk server layer. 
                    When the ODUflex(GFP) connection is initially created, this represents the actual number of tributary slots in use for the connection. When an ODUflex(GFP) connection is undergoing a resize operation, this attribute reflects the desired (resized) number of tributary slots only after the following stages (see G.7044[5] for details):
                    - After the Bandwidth Resize (BWR) phase completes (In the case of bandwidth increase)
                    - After the Link Connection Resize (LCR) phase of the ODUflex resize operation (in the case of bandwidth decrease)
                    This attribute applies only to ODUflex(CBR) connections only. The value of this attribute is (239/238)* (Bit rate of the CBR client).
                    ";
            }
            container nominalBitRateAndTolerance {
                uses ODUk_h_nominalBitRateAndTolerance;
                description "This attribute specifies the nominal clock frequency and its tolerance range. Valid values for the frequency (in kHz) and tolerance (in ppm) range are given in Table 14-2/G.798 and clause 12.2.5/G.709.";
            }
            description "none";
        }
        grouping OduTerminationSpec {
            leaf rate {
                type string;
                config false;
                description "This attribute applies only to ODUflex(CBR) connections only. The value of this attribute is (239/238)* (Bit rate of the CBR client).
                    ";
            }
            leaf dmSource {
                type boolean;
                description "This attribute is for configuring the delay measurement process at the trail termination function represented by the subject TTP object class. It models the MI_DM_Source MI signal. If MI_DM_Source is false, then the value of the DMp bit is determined by the RI_DM. If MI_DM_Source is true, then the value of the DMp bit is set to MI_DMValue.";
            }
            leaf dmValue {
                type boolean;
                description "This attribute is for setting the DMp and DMti bits of the delay measurement process. The value of true sets the DMp and DMti bits to 0 and the value of false to 1.";
            }
            leaf-list tcmFieldsInUse {
                type uint64;
                config false;
                description "This attribute indicates the used TCM fields of the ODUk OH.";
            }
            leaf acti {
                type BitString;
                config false;
                description "The Trail Trace Identifier (TTI) information recovered (Accepted) from the TTI overhead position at the sink of a trail.";
            }
            leaf degM {
                type uint64;
                description "This attribute indicates the threshold level for declaring a Degraded Signal defect (dDEG). A dDEG shall be declared if DegM consecutive bad PM Seconds are detected.";
            }
            container degThr {
                uses DegThr;
                description "This attribute indicates the threshold level for declaring a performance monitoring (PM) Second to be bad. The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.";
            }
            leaf exDapi {
                type BitString;
                description "The Expected Destination Access Point Identifier (ExDAPI), provisioned by the managing system, to be compared with the TTI accepted at the overhead position of the sink for the purpose of checking the integrity of connectivity.";
            }
            leaf exSapi {
                type BitString;
                description "The Expected Source Access Point Identifier (ExSAPI), provisioned by the managing system, to be compared with the TTI accepted at the overhead position of the sink for the purpose of checking the integrity of connectivity.";
            }
            leaf timActDisabled {
                type boolean;
                description "This attribute provides the control capability for the managing system to enable or disable the Consequent Action function when detecting Trace Identifier Mismatch (TIM) at the trail termination sink. The value of TRUE means disabled.";
            }
            leaf timDetMode {
                type TimDetMo;
                description "This attribute indicates the mode of the Trace Identifier Mismatch (TIM) Detection functionallowed values: off, SAPIonly, DAPIonly, SAPIandDAPI";
            }
            leaf txti {
                type BitString;
                description "The Trail Trace Identifier (TTI) information, provisioned by the managing system at the termination source, to be placed in the TTI overhead position of the source of a trail for transmission.";
            }
            description "none";
        }
        list OduLpSpec {
            key 'extensionsSpecification';
            container _adapterSpec {
                uses OduAdapterAndConnectionPointSpec;
                description "none";
            }
            container _terminationSpec {
                uses OduTerminationSpec;
                description "none";
            }
            container _oduPoolPropertySpec {
                uses OduPoolPropertySpec;
                description "none";
            }
            leaf extensionsSpecReference {
                type string;
                default "/Tapi:Context/Tapi:OduSpec";
                description "none";
            }
            leaf extensionsSpecTarget {
                type string;
                default "/Tapi-ObjectClasses:Context/Tapi-ObjectClasses:_serviceEndPoint/Tapi-ObjectClasses:_connectionEndPoint/Tapi-ObjectClasses:_layerProtocol/Tapi-ObjectClasses:_lpSpecData";
                description "none";
            }
            uses Tapi:ExtensionsSpec;
            description "none";
        }
        grouping OduPoolPropertySpec {
            description "none";
        }
    
    /***********************
    * package TypeDefinitions
    **********************/ 
        typedef BitString {
            type string;
            description "This primitive type defines a bit oriented string.
                The size of the BitString will be defined in the valueRange property of the attribute; according to ASN.1 (X.680).
                The semantic of each bit position will be defined in the Documentation field of the attribute.";
        }
        grouping DegThr {
            leaf degThrValue {
                type string;
                description "Percentage of detected errored blocks";
            }
            leaf degThrType {
                type string;
                description "Number of errored blocks";
            }
            leaf percentageGranularity {
                type string;
                description "none";
            }
            description "Degraded Threshold, specify either the percentage or the number of Errored Blocks in the defined interval. 
                degThrValue when type is PERCENTAGE:
                percentageGranularity is used to indicate the number of decimal points
                So if percentageGranularity is 0 a value of 1 in degThrValue would indicate 1%, a value of 10 = 10%, a value of 100 = 100%
                So if percentageGranularity is 3 (thousandths) a value of 1 in degThrValue would indicate 0.001%, a value of 1000 = 1%, a value of 1000000 = 100%
                degThrValue when type is NUMBER_ERROR_BLOCKS:
                Number of Errored Blocks is captured in an integer value.";
        }
        typedef ODUk_TtpKBitRate {
            type enumeration {
                enum 1.25_G {
                    description "none";
                }
                enum 2.5_G {
                    description "none";
                }
                enum 10_G {
                    description "none";
                }
                enum 10_G_2E {
                    description "none";
                }
                enum 40_G {
                    description "none";
                }
                enum 100_G {
                    description "none";
                }
                enum FLEX_CBR {
                    description "Represents ODUflex connection which carry a CBR client";
                }
                enum FLEX_GFP {
                    description "Represents ODUflex connection which carry packet traffic";
                }
            }
            description "Provides an enumeration with the meaning of each k value.";
        }
        typedef ODUk_TcmOrGccChoice {
            type string;
            description "A data type to constrain the values to particular types of ODUk CTPs.";
        }
        typedef TimDetMo {
            type enumeration {
                enum DAPI {
                    description "none";
                }
                enum SAPI {
                    description "none";
                }
                enum BOTH {
                    description "none";
                }
            }
            description "List of modes for trace identifier mismatch detection.";
        }
        typedef ODUk_h_ResizingProtocolStatus {
            type enumeration {
                enum LCR_INITIATED {
                    description "none";
                }
                enum LCR_FAILED {
                    description "none";
                }
                enum LCR_COMPLETED {
                    description "none";
                }
                enum BWR_INITIATED {
                    description "none";
                }
                enum BWR_COMPLETED {
                    description "none";
                }
            }
            description "The valid status' of the resizing protocol.";
        }
        typedef ODUk_CtpProblemList {
            type enumeration {
                enum PLM {
                    description "Payload Mismatch";
                }
                enum MSIM {
                    description "MultiplexStructureIdentifier Mismatch, per time slot";
                }
                enum LOF_LOM {
                    description "Loss of Frame, Loss of Multiframe, per time slot";
                }
                enum LOOMFI {
                    description "Loss of OPU Multiframe Indicator";
                }
            }
            description "The valid list of problems for the entity.";
        }
        typedef ODUk_CtpKBitRate {
            type enumeration {
                enum 1.25_G {
                    description "none";
                }
                enum 2.5_G {
                    description "none";
                }
                enum 10_G {
                    description "none";
                }
                enum 10_G_2E {
                    description "2e represents an approximate bit rate of 10 Gbit/s as a logical wrapper 10GBASE-R";
                }
                enum 40_G {
                    description "2e represents an approximate bit rate of 10 Gbit/s as a logical wrapper 10GBASE-R";
                }
                enum 100_G {
                    description "2e represents an approximate bit rate of 10 Gbit/s as a logical wrapper 10GBASE-R";
                }
                enum FLEX_CBR {
                    description "Represents ODUflex connection which carry a CBR client";
                }
                enum FLEX_GFP {
                    description "Represents ODUflex connection which carry packet traffic";
                }
            }
            description "Provides an enumeration with the meaning of each k value.";
        }
        grouping ODUk_h_nominalBitRateAndTolerance {
            leaf tolerance {
                type uint64;
                description "tolerance in ppm";
            }
            leaf frequency {
                type string;
                description "frequency in kilohertz";
            }
            description "Valid values for the frequency (in kHz) and tolerance (in ppm) range are given in Table 14-2/G.798 and clause 12.2.5/G.709.";
        }
        typedef TcmMode {
            type enumeration {
                enum OPERATIONAL {
                    description "none";
                }
                enum TRANSPARENT {
                    description "none";
                }
                enum MONITOR {
                    description "none";
                }
            }
            description "List of value modes for the sink side of the tandem connection monitoring function.";
        }
        typedef ODUkT_tcmExtension {
            type enumeration {
                enum NORMAL {
                    description "none";
                }
                enum PASS-THROUGH {
                    description "none";
                }
                enum ERASE {
                    description "none";
                }
            }
            description "none";
        }
        typedef ODUkT_AdministrationState {
            type enumeration {
                enum LOCKED {
                    description "none";
                }
                enum NORMAL {
                    description "none";
                }
            }
            description "The list of valid adminstration states.";
        }
        typedef ODUk_TcmStatus {
            type enumeration {
                enum NO_SOURCE_TC {
                    description "TCM byte 3 (bits 6 7 8) -- 0 0 0, No source Tandem Connection";
                }
                enum IN_USE_WITHOUT_IAE {
                    description "TCM byte 3 (bits 6 7 8) -- 0 0 1,  In use without IAE (Incoming Alignment Error)";
                }
                enum IN_USE_WITH_IAE {
                    description "TCM byte 3 (bits 6 7 8) -- 0 1 0, In use with IAE (Incoming Alignment Error)";
                }
                enum RESERVED_1 {
                    description "TCM byte 3 (bits 6 7 8) -- 0 1 1, Reserved for future international standardization";
                }
                enum RESERVED_2 {
                    description "TCM byte 3 (bits 6 7 8) -- 1 0 0, Reserved for future international standardization";
                }
                enum LCK {
                    description "TCM byte 3 (bits 6 7 8) -- 1 0 1, Maintenance signal: ODUk-LCK";
                }
                enum OCI {
                    description "TCM byte 3 (bits 6 7 8) -- 1 1 0, Maintenance signal: ODUk-OCI";
                }
                enum AIS {
                    description "TCM byte 3 (bits 6 7 8) -- 1 1 1, Maintenance signal: ODUk-AIS";
                }
            }
            description "See Table 15-5/G.709/Y.1331 ";
        }
    
}
