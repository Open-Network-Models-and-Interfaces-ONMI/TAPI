module tapi-physical-route {
    yang-version "1.1";
    namespace "urn:onf:otcc:yang:tapi-physical-route";
    prefix tapi-physical-route;
    import tapi-common {
        prefix tapi-common;
    }
    import tapi-notification {
        prefix tapi-notification;
    }
    import tapi-streaming {
        prefix tapi-streaming;
    }
    import tapi-connectivity {
        prefix tapi-connectivity;
    }
    import tapi-equipment {
        prefix tapi-equipment;
    }
    organization "Linux Foundation ONMI (Open Network Modeling and Interfaces) Project";
    contact "
         Project Web: <https://github.com/Open-Network-Models-and-Interfaces-ONMI/onmi-home/wiki>
         Project List: <mailto:onmi-tapi@googlegroups.com>
         Editor: Nigel Davis <mailto:ndavis@ciena.com>
         Arturo Mayoral <mailto:amayoral@telecominfraproject.com>
         Ramon Casellas <mailto:ramon.casellas@cttc.es>";
    description "
        This module contains TAPI physical route extensions Model definitions.
        Source: TapiPhysicalRoute.uml
        - The TAPI YANG models included in this TAPI release are a *normative* part of the TAPI SDK.
        - The YANG specifications have been generated from the corresponding UML model using the [EAGLE UML2YANG mapping tool]
        <https://github.com/Open-Network-Models-and-Interfaces-ONMI/onmi-iisomi-uml-yang>
        and further edited manually to comply with the [ONMI IISOMI UML2YANG mapping guidelines]
        <https://github.com/Open-Network-Models-and-Interfaces-ONMI/onmi-iisomi-home>
        - Status of YANG model artifacts can be determined by referring to the corresponding UML artifacts.
        As described in the UML models, some artifacts are considered *experimental*, and thus the corresponding YANG artifacts.
        - The LF ONMI TAPI release process does not guarantee backward compatibility of YANG models across major versions of TAPI releases.
        The YANG model backward compatibility criteria are outlined in section 11 of <https://tools.ietf.org/html/rfc7950>.
        YANG models included in this release may not be backward compatible with some previous TAPI releases.
        - Previous revisions can now be found at https://github.com/Open-Network-Models-and-Interfaces-ONMI/TAPI under the 
        appropriate tag and, where relevant, fixes to those revisions can be found under the corresponding branches. The documentation for
        each significant revision is found at https://github.com/Open-Network-Models-and-Interfaces-ONMI/TAPI-Documentation under the
        appropriate tag and, where relevant, fixes to those revisions can be found under the corresponding branches.
        License: This module is distributed under the Apache License 2.0.";
    revision 2025-12-31 {
        description "LF ONMI Transport API version 2.1.5
                   Changes included in this TAPI release (v2.1.5) are listed in
                   <https://github.com/Open-Network-Models-and-Interfaces-ONMI/TAPI-Documentation/tree/v2.1.5/DeltaDocument>";
        reference "ONF-TR-527, ONF-TR-512, ONF-TR-531, RFC 7950, RFC 6087 and LF ONMI TAPI UML model
                  <https://github.com/Open-Network-Models-and-Interfaces-ONMI/TAPI/tree/v2.1.5/UML>";
    }

	
	
    augment "/tapi-common:context/tapi-connectivity:connectivity-context/tapi-connectivity:connection" {
        container physical-route-list {
            uses physical-route-list;
            description "This augment allows Connection to describe its physical route(s) by listing all involved AccessPorts, despite TapiConnectivity model does not import TapiEquipment model.";
        }
        description "This augment allows Connection to describe its physical route(s) by listing all involved AccessPorts, despite TapiConnectivity model does not import TapiEquipment model.";
    }
    augment "/tapi-common:context/tapi-notification:notification-context/tapi-notification:notification" {
        when 'derived-from-or-self(tapi-notification:target-object-type, "EQUIPMENT_OBJECT_TYPE_PHYSICAL_ROUTE")';
        container physical-route {
            uses physical-route;
            description "none";
        }
        description "none";
    }
    augment "/tapi-streaming:stream-record/tapi-streaming:log-record/tapi-streaming:log-record-body" {
        when 'derived-from-or-self(tapi-streaming:record-content, "EQUIPMENT_OBJECT_TYPE_PHYSICAL_ROUTE")';
        container physical-route {
            uses physical-route;
            description "none";
        }
        description "none";
    }
    augment "/tapi-common:context/tapi-notification:notification-context/tapi-notification:notification" {
        when 'derived-from-or-self(tapi-notification:target-object-type, "EQUIPMENT_OBJECT_TYPE_PHYSICAL_ROUTE_ELEMENT")';
        container physical-route-element {
            uses physical-route-element;
            description "none";
        }
        description "none";
    }
    augment "/tapi-streaming:stream-record/tapi-streaming:log-record/tapi-streaming:log-record-body" {
        when 'derived-from-or-self(tapi-streaming:record-content, "EQUIPMENT_OBJECT_TYPE_PHYSICAL_ROUTE_ELEMENT")';
        container physical-route-element {
            uses physical-route-element;
            description "none";
        }
        description "none";
    }
 


    augment "/tapi-notification:notification" {
        when 'derived-from-or-self(tapi-notification:target-object-type, "EQUIPMENT_OBJECT_TYPE_PHYSICAL_ROUTE")';
        container physical-route {
            uses physical-route;
            description "none";
        }
        description "none";
    }
    augment "/tapi-notification:notification" {
        when 'derived-from-or-self(tapi-notification:target-object-type, "EQUIPMENT_OBJECT_TYPE_PHYSICAL_ROUTE_ELEMENT")';
        container physical-route-element {
            uses physical-route-element;
            description "none";
        }
        description "none";
    }




    /**************************
    * definitions of references
    **************************/


    /**************************
    * package type-definitions
    **************************/ 

    identity EQUIPMENT_OBJECT_TYPE_PHYSICAL_ROUTE {
        base tapi-equipment:EQUIPMENT_OBJECT_TYPE;
        description "none";
    }
    identity EQUIPMENT_OBJECT_TYPE_PHYSICAL_ROUTE_ELEMENT {
        base tapi-equipment:EQUIPMENT_OBJECT_TYPE;
        description "none";
    }


    identity PHYSICAL_ROUTE_STATE {
        description "none";
    }
    identity PHYSICAL_ROUTE_STATE_CURRENT {
        base PHYSICAL_ROUTE_STATE;
        description "The PhysicalRoute instance identified is the current PhysicalRoute, i.e., is the one that is active and selected to support service.";
    }
    identity PHYSICAL_ROUTE_STATE_NOT_CURRENT {
        base PHYSICAL_ROUTE_STATE;
        description "The PhysicalRoute instance is not the one supporting the service.";
    }
    identity PHYSICAL_ROUTE_STATE_UNKNOWN {
        base PHYSICAL_ROUTE_STATE;
        description "The PhysicalRoute state is unknown.";
    }
    typedef physical-route-state {
        type identityref {
            base PHYSICAL_ROUTE_STATE;
        }
        description "Potential PhysicalRoute states concerning the service support.";
    }


    /**************************
    * package object-classes
    **************************/ 

    grouping physical-route {
        list physical-route-element {
            config false;
            uses physical-route-element;
            description "A point in the PhysicalRoute. A PhysicalRoute must have at least one point.";
        }
        leaf physical-route-state {
            type physical-route-state;
            default "PHYSICAL_ROUTE_STATE_CURRENT";
            config false;
            description "Provides optional resilience and state attributes to the PhysicalRoute.
                CONDITION: Mandatory where not always default.";
        }
        uses tapi-common:local-class;
        description "The physical route of a connection is modeled as an ordered sequence of physical route element instances.
            The physical route is a description dedicated to the connection.";
    }
    grouping physical-route-list {
        list physical-route {
            key 'local-id';
            config false;
            uses physical-route;
            description "List of PhysicalRoutes composing the physical route of the Connection.
                CONDITION: Mandatory where a physical route is to be conveyed.";
        }
        description "The list of the PhysicalRoutes of a Connection.";
    }

    grouping physical-route-element {
        container access-port-in-route {
            uses tapi-equipment:access-port-ref;
            config false;
            description "The AccessPort included in the physical route.
                CONDITION: Mandatory where AccessPort is used to define physical route.";
        }
        list connector-pin-in-route {
            /* key 'device-uuid equipment-uuid connector-identification pin-identification'; */
            /* the reference to equipment is used as a key, but the key statement does not accept container, but only leafs.
            Hence the two leafs of the equipment-ref have been explicitly specified.*/
            config false;
            uses tapi-equipment:connector-pin-address;
            description "The connectors and pins defining this point in the route where the access port alone is not sufficient or the access port is not provided.
                CONDITION: Mandatory where AccessPort is not used to define PhysicalRoute or where AccessPort requires clarification as it includes more connectorPins than are used in the route.";
        }
        description "A PhysicalRouteElement describes equipment, connectors on those equipments and pins of those connectors that are involved in the physical route of the connection. 
            The description may be in terms of access port or connector pin in route (at least one of access port or connector pin in route must be provided) or both.
            Where access port is provided alone, this may be because all pins in the connectors of the access port are used, because the connector pin detail id not known the and to its subset of connectorPins which are involved in the physical route. 
            An access port may include connectorPins of more Equipments, e.g., in case of bidirectional access port shared by two 'unidirectional'; Equipments.
            Connector pin details may be provided alone without an access port where there are no access ports modelled.";
    }
 
}
