module TapiSpec-ObjectClasses {
    namespace "urn:ONF:TapiSpec-ObjectClasses";
    prefix TapiSpec-ObjectClasses;
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-08 {
        description "Latest revision";
        reference "RFC 6020 and RFC 6087";
    }
    grouping LpSpec {
        leaf lpSpecReference {
            type string;
            description "none";
        }
        description "none";
    }
    grouping LtpSpec {
        leaf ltpSpecReference {
            type string;
            description "none";
        }
        leaf-list lpSpecReference {
            type string;
            min-elements 1;
            description "none";
        }
        description "none";
    }
}
