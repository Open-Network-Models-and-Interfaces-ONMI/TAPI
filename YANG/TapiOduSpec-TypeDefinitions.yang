module TapiOduSpec-TypeDefinitions {
    namespace "urn:ONF:TapiOduSpec-TypeDefinitions";
    prefix TapiOduSpec-TypeDefinitions;
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-08 {
        description "Latest revision";
        reference "RFC 6020 and RFC 6087";
    }
    typedef BitString {
        type string;
        description "This primitive type defines a bit oriented string.
            The size of the BitString will be defined in the valueRange property of the attribute; according to ASN.1 (X.680).
            The semantic of each bit position will be defined in the Documentation field of the attribute.";
    }
    grouping DegThr {
        leaf degThrValue {
            type string;
            description "Percentage of detected errored blocks";
        }
        leaf degThrType {
            type string;
            description "Number of errored blocks";
        }
        leaf percentageGranularity {
            type string;
            description "none";
        }
        description "Degraded Threshold, specify either the percentage or the number of Errored Blocks in the defined interval. 
            degThrValue when type is PERCENTAGE:
            percentageGranularity is used to indicate the number of decimal points
            So if percentageGranularity is 0 a value of 1 in degThrValue would indicate 1%, a value of 10 = 10%, a value of 100 = 100%
            So if percentageGranularity is 3 (thousandths) a value of 1 in degThrValue would indicate 0.001%, a value of 1000 = 1%, a value of 1000000 = 100%
            degThrValue when type is NUMBER_ERROR_BLOCKS:
            Number of Errored Blocks is captured in an integer value.";
    }
    typedef ODUk_TtpKBitRate {
        type enumeration {
            enum 1.25_G {
                description "none";
            }
            enum 2.5_G {
                description "none";
            }
            enum 10_G {
                description "none";
            }
            enum 10_G_2E {
                description "none";
            }
            enum 40_G {
                description "none";
            }
            enum 100_G {
                description "none";
            }
            enum FLEX_CBR {
                description "Represents ODUflex connection which carry a CBR client";
            }
            enum FLEX_GFP {
                description "Represents ODUflex connection which carry packet traffic";
            }
        }
        description "Provides an enumeration with the meaning of each k value.";
    }
    typedef ODUk_TcmOrGccChoice {
        type string;
        description "A data type to constrain the values to particular types of ODUk CTPs.";
    }
    typedef TimDetMo {
        type enumeration {
            enum DAPI {
                description "none";
            }
            enum SAPI {
                description "none";
            }
            enum BOTH {
                description "none";
            }
        }
        description "List of modes for trace identifier mismatch detection.";
    }
    typedef ODUk_h_ResizingProtocolStatus {
        type enumeration {
            enum LCR_INITIATED {
                description "none";
            }
            enum LCR_FAILED {
                description "none";
            }
            enum LCR_COMPLETED {
                description "none";
            }
            enum BWR_INITIATED {
                description "none";
            }
            enum BWR_COMPLETED {
                description "none";
            }
        }
        description "The valid status' of the resizing protocol.";
    }
    typedef ODUk_CtpProblemList {
        type enumeration {
            enum PLM {
                description "Payload Mismatch";
            }
            enum MSIM {
                description "MultiplexStructureIdentifier Mismatch, per time slot";
            }
            enum LOF_LOM {
                description "Loss of Frame, Loss of Multiframe, per time slot";
            }
            enum LOOMFI {
                description "Loss of OPU Multiframe Indicator";
            }
        }
        description "The valid list of problems for the entity.";
    }
    typedef ODUk_CtpKBitRate {
        type enumeration {
            enum 1.25_G {
                description "none";
            }
            enum 2.5_G {
                description "none";
            }
            enum 10_G {
                description "none";
            }
            enum 10_G_2E {
                description "2e represents an approximate bit rate of 10 Gbit/s as a logical wrapper 10GBASE-R";
            }
            enum 40_G {
                description "2e represents an approximate bit rate of 10 Gbit/s as a logical wrapper 10GBASE-R";
            }
            enum 100_G {
                description "2e represents an approximate bit rate of 10 Gbit/s as a logical wrapper 10GBASE-R";
            }
            enum FLEX_CBR {
                description "Represents ODUflex connection which carry a CBR client";
            }
            enum FLEX_GFP {
                description "Represents ODUflex connection which carry packet traffic";
            }
        }
        description "Provides an enumeration with the meaning of each k value.";
    }
    grouping ODUk_h_nominalBitRateAndTolerance {
        leaf tolerance {
            type uint64;
            description "tolerance in ppm";
        }
        leaf frequency {
            type string;
            description "frequency in kilohertz";
        }
        description "Valid values for the frequency (in kHz) and tolerance (in ppm) range are given in Table 14-2/G.798 and clause 12.2.5/G.709.";
    }
    typedef TcmMode {
        type enumeration {
            enum OPERATIONAL {
                description "none";
            }
            enum TRANSPARENT {
                description "none";
            }
            enum MONITOR {
                description "none";
            }
        }
        description "List of value modes for the sink side of the tandem connection monitoring function.";
    }
    typedef ODUkT_tcmExtension {
        type enumeration {
            enum NORMAL {
                description "none";
            }
            enum PASS-THROUGH {
                description "none";
            }
            enum ERASE {
                description "none";
            }
        }
        description "none";
    }
    typedef ODUkT_AdministrationState {
        type enumeration {
            enum LOCKED {
                description "none";
            }
            enum NORMAL {
                description "none";
            }
        }
        description "The list of valid adminstration states.";
    }
    typedef ODUk_TcmStatus {
        type enumeration {
            enum NO_SOURCE_TC {
                description "TCM byte 3 (bits 6 7 8) -- 0 0 0, No source Tandem Connection";
            }
            enum IN_USE_WITHOUT_IAE {
                description "TCM byte 3 (bits 6 7 8) -- 0 0 1,  In use without IAE (Incoming Alignment Error)";
            }
            enum IN_USE_WITH_IAE {
                description "TCM byte 3 (bits 6 7 8) -- 0 1 0, In use with IAE (Incoming Alignment Error)";
            }
            enum RESERVED_1 {
                description "TCM byte 3 (bits 6 7 8) -- 0 1 1, Reserved for future international standardization";
            }
            enum RESERVED_2 {
                description "TCM byte 3 (bits 6 7 8) -- 1 0 0, Reserved for future international standardization";
            }
            enum LCK {
                description "TCM byte 3 (bits 6 7 8) -- 1 0 1, Maintenance signal: ODUk-LCK";
            }
            enum OCI {
                description "TCM byte 3 (bits 6 7 8) -- 1 1 0, Maintenance signal: ODUk-OCI";
            }
            enum AIS {
                description "TCM byte 3 (bits 6 7 8) -- 1 1 1, Maintenance signal: ODUk-AIS";
            }
        }
        description "See Table 15-5/G.709/Y.1331 ";
    }
}
