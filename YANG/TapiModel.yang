module TapiModel {
    namespace "urn:onf:params:xml:ns:yang:TapiModel";
    prefix TapiModel;
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-07-11 {
        description "Latest revision";
        reference "RFC 6020 and RFC 6087";
    }
}
