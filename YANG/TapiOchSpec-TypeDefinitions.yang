module TapiOchSpec-TypeDefinitions {
    namespace "urn:ONF:TapiOchSpec-TypeDefinitions";
    prefix TapiOchSpec-TypeDefinitions;
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-08 {
        description "Latest revision";
        reference "RFC 6020 and RFC 6087";
    }
    grouping ApplicationIdentifier {
        leaf applicationIdentifierType {
            type string;
            description "none";
        }
        leaf applicationIdentifierValue {
            type string;
            description "none";
        }
        description "none";
    }
    typedef MonitoredDirection {
        type enumeration {
            enum SINK {
                description "none";
            }
            enum SOURCE {
                description "none";
            }
        }
        description "The enumeration with the options for directionality for nonintrusive monitoring.";
    }
    grouping NominalCentralFrequencyOrWavelength {
        leaf linkType {
            type string;
            description "none";
        }
        leaf nominalCentralFrequencyOrWavelength {
            type string;
            description "none";
        }
        description "none";
    }
}
