module TapiPathComputation {
    namespace "urn:onf:params:xml:ns:yang:TapiPathComputation";
    prefix TapiPathComputation;
    import TapiTopology {
        prefix TapiTopology;
    }
    import Tapi {
        prefix Tapi;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-07-19 {
        description "Latest revision";
        reference "RFC 6020 and RFC 6087";
    }
    augment "/Tapi:Context/Tapi:_path" {
        uses Path;
        description "none";
    }
    augment "/Tapi:Context/Tapi:_pathCompService" {
        uses PathComputationService;
        description "none";
    }
    /***********************
    * package ObjectClasses
    **********************/ 
        grouping Path {
            list _telink {
                key 'localId';
                config false;
                uses TapiTopology:TeLink;
                description "none";
            }
            container _routingConstraint {
                config false;
                uses RoutingConstraint;
                description "none";
            }
            uses Tapi:ResourceSpec;
            description "Path is described by an ordered list of TE Links. A TE Link is defined by a pair of Node/NodeEdgePoint IDs. A Connection is realized by concatenating link resources (associated with a Link) and the lower-level connections (cross-connections) in the different nodes";
        }
        grouping PathCompServicePort {
            leaf _serviceEndPoint {
                type leafref {
                    path '/Tapi:Context/Tapi:_serviceEndPoint/Tapi:uuid';
                }
                config false;
                description "none";
            }
            leaf role {
                type Tapi:PortRole;
                config false;
                description "Each EP of the FC has a role (e.g., working, protection, protected, symmetric, hub, spoke, leaf, root)  in the context of the FC with respect to the FC function. ";
            }
            leaf direction {
                type Tapi:PortDirection;
                config false;
                description "The orientation of defined flow at the EndPoint.";
            }
            leaf serviceLayer {
                type Tapi:LayerProtocolName;
                config false;
                description "none";
            }
            uses Tapi:LocalClass;
            description "The association of the FC to LTPs is made via EndPoints.
                The EndPoint (EP) object class models the access to the FC function. 
                The traffic forwarding between the associated EPs of the FC depends upon the type of FC and may be associated with FcSwitch object instances.  
                In cases where there is resilience the EndPoint may convey the resilience role of the access to the FC. 
                It can represent a protected (resilient/reliable) point or a protecting (unreliable working or protection) point.
                The EP replaces the Protection Unit of a traditional protection model. 
                The ForwadingConstruct can be considered as a component and the EndPoint as a Port on that component";
        }
        grouping PathComputationService {
            leaf-list _path {
                type leafref {
                    path '/Tapi:Context/Tapi:_path/Tapi:uuid';
                }
                config false;
                description "none";
            }
            list _servicePort {
                key 'localId';
                uses PathCompServicePort;
                description "none";
            }
            container _routingConstraint {
                uses RoutingConstraint;
                description "none";
            }
            container _objectiveFunction {
                uses PathObjectiveFunction;
                description "none";
            }
            container _optimizationConstraint {
                uses PathOptimizationConstraint;
                description "none";
            }
            uses Tapi:ServiceSpec;
            description "none";
        }
        grouping PathObjectiveFunction {
            leaf bandwidthOptimization {
                type Tapi:DirectiveValue;
                config false;
                description "none";
            }
            leaf concurrentPaths {
                type Tapi:DirectiveValue;
                config false;
                description "none";
            }
            leaf costOptimization {
                type Tapi:DirectiveValue;
                config false;
                description "none";
            }
            leaf linkUtilization {
                type Tapi:DirectiveValue;
                config false;
                description "none";
            }
            leaf resourceSharing {
                type Tapi:DirectiveValue;
                config false;
                description "none";
            }
            uses Tapi:LocalClass;
            description "none";
        }
        grouping PathOptimizationConstraint {
            leaf trafficInterruption {
                type Tapi:DirectiveValue;
                config false;
                description "none";
            }
            uses Tapi:LocalClass;
            description "none";
        }
        grouping RoutingConstraint {
            container requestedCapacity {
                config false;
                uses TapiTopology:Capacity;
                description "none";
            }
            leaf serviceLevel {
                type string;
                config false;
                description "An abstract value the meaning of which is mutually agreed – typically represents metrics such as - Class of service, priority, resiliency, availability";
            }
            leaf-list pathLayer {
                type Tapi:LayerProtocolName;
                config false;
                description "none";
            }
            list costCharacteristic {
                key 'costName costValue costAlgorithm';
                config false;
                uses TapiTopology:CostCharacteristic;
                description "The list of costs where each cost relates to some aspect of the TopologicalEntity.";
            }
            list latencyCharacteristic {
                key 'trafficPropertyName trafficPropertyQueingLatency';
                config false;
                uses TapiTopology:LatencyCharacteristic;
                description "The effect on the latency of a queuing process. This only has significant effect for packet based systems and has a complex characteristic.";
            }
            leaf-list _includeTopology {
                type leafref {
                    path '/Tapi:Context/Tapi:_topology/Tapi:uuid';
                }
                config false;
                description "none";
            }
            leaf-list _avoidTopology {
                type leafref {
                    path '/Tapi:Context/Tapi:_topology/Tapi:uuid';
                }
                config false;
                description "none";
            }
            list _includePath {
                key 'localId';
                config false;
                uses TapiTopology:TeLink;
                description "none";
            }
            list _excludePath {
                key 'localId';
                config false;
                uses TapiTopology:TeLink;
                description "none";
            }
            uses Tapi:LocalClass;
            description "none";
        }
    
    /***********************
    * package Interfaces
    **********************/ 
        rpc computeP2PPath {
            description "none";
            input {
                list servicePort {
                    min-elements 2;
                    max-elements 2;
                    uses PathCompServicePort;
                    description "none";
                }
                container routingConstraint {
                    uses RoutingConstraint;
                    description "none";
                }
                container objectiveFunction {
                    uses PathObjectiveFunction;
                    description "none";
                }
            }
            output {
                container pathCompService {
                    uses PathComputationService;
                    description "none";
                }
            }
        }
        rpc optimizeP2PPath {
            description "none";
            input {
                leaf pathIdOrName {
                    type string;
                    description "none";
                }
                container routingConstraint {
                    uses RoutingConstraint;
                    description "none";
                }
                container optimizationConstraint {
                    uses PathOptimizationConstraint;
                    description "none";
                }
                container objectiveFunction {
                    uses PathObjectiveFunction;
                    description "none";
                }
            }
            output {
                container pathCompService {
                    uses PathComputationService;
                    description "none";
                }
            }
        }
        rpc deleteP2PPath {
            description "none";
            input {
                leaf pathIdOrName {
                    type string;
                    description "none";
                }
            }
            output {
                container pathCompService {
                    uses PathComputationService;
                    description "none";
                }
            }
        }
    
}
