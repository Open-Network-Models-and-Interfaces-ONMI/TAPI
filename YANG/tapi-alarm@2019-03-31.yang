module tapi-alarm {
    namespace "urn:onf:otcc:yang:tapi-alarm";
    prefix tapi-alarm;
    import tapi-common {
        prefix tapi-common;
    }
    import tapi-oam {
        prefix tapi-oam;
    }
    import tapi-notification {
        prefix tapi-notification;
    }
    organization "ONF OTCC (Open Transport Configuration & Control) Project";
    contact "
         Project Web: <https://wiki.opennetworking.org/display/OTCC/TAPI>
         Project List: <mailto:transport-api@opennetworking.org>
         Editor: Karthik Sethuraman
                 <mailto:karthik.sethuraman@necam.com>";
    description "
        This module contains TAPI Alarm Model definitions.
        Source: TapiAlarm.uml
        Copyright (c) 2018 Open Networking Foundation (ONF). All rights reserved.
        License: This module is distributed under the Apache License 2.0
        - The TAPI YANG models included in this TAPI release are a *normative* part of the TAPI SDK.
        - The YANG specifications have been generated from the corresponding UML model using the [ONF EAGLE UML2YANG mapping tool]
        <https://github.com/OpenNetworkingFoundation/EagleUmlYang>
        and further edited manually to comply with the [ONF IISOMI UML2YANG mapping guidelines]
        <https://wiki.opennetworking.org/display/OIMT/UML+-+YANG+Guidelines>
        - Status of YANG model artifacts can be determined by referring to the corresponding UML artifacts.
        As described in the UML models, some artifacts are considered *experimental*, and thus the corresponding YANG artifacts.
        - The ONF TAPI release process does not guarantee backward compatibility of YANG models across major versions of TAPI releases.
        The YANG model backward compatibility criteria are outlined in section 11 of <https://tools.ietf.org/html/rfc7950>.
        YANG models included in this release may not be backward compatible with previous TAPI releases.";
    revision 2019-03-31 {
        description "ONF Transport API version 2.2-RC1.
                   Changes included in this TAPI release (v2.2) are listed in
                  <https://github.com/OpenNetworkingFoundation/TAPI/blob/develop/CHANGE_LOG/change-log.2.2.md>";
        reference "ONF-TR-527, ONF-TR-512, ONF-TR-531, RFC 7950, RFC 6087 and ONF TAPI UML model
                  <https://github.com/OpenNetworkingFoundation/TAPI/tree/v2.2.0/UML>";
    }
    revision 2018-12-10 {
        description "ONF Transport API version 2.1.1.
                   Changes included in this TAPI release (v2.1.1) are listed in
                  <https://github.com/OpenNetworkingFoundation/TAPI/blob/develop/CHANGE_LOG/change-log.2.1.1.md>";
        reference "ONF-TR-527, ONF-TR-512, ONF-TR-531, RFC 7950, RFC 6087 and ONF TAPI UML model
                  <https://github.com/OpenNetworkingFoundation/TAPI/tree/v2.1.1/UML>";
    }
    revision 2018-10-16 {
        description "ONF Transport API version 2.1.0.
                   Changes included in this TAPI release (v2.1.0) are listed in
                  <https://github.com/OpenNetworkingFoundation/TAPI/blob/develop/CHANGE_LOG/change-log.2.1.0.md>";
        reference "ONF-TR-527, ONF-TR-512, ONF-TR-531, RFC 7950, RFC 6087 and ONF TAPI UML model
                  <https://github.com/OpenNetworkingFoundation/TAPI/tree/v2.1.0/UML>";
    }
    revision 2018-03-07 {
        description "ONF Transport API version 2.0.2
        This YANG module has been generated from the TAPI UML Model using the IISOMI-Eagle xmi2yang mapping tool.
        Changes in this revision: <https://github.com/OpenNetworkingFoundation/TAPI/blob/develop/CHANGE_LOG/change-log.2.0.2.md>";
        reference "ONF-TR-527, ONF-TR-512, ONF-TR-531, RFC 6020, RFC 6087 and ONF TAPI UML model
                  <https://github.com/OpenNetworkingFoundation/TAPI/tree/v2.0.2/UML>";
    }
    revision 2018-02-16 {
        description "ONF Transport API version 2.0.1
        This YANG module has been generated from the TAPI UML Model using the IISOMI-Eagle xmi2yang mapping tool.
        Changes in this revision: <https://github.com/OpenNetworkingFoundation/TAPI/blob/develop/CHANGE_LOG/change-log.2.0.1.md>";
        reference "ONF-TR-527, ONF-TR-512, ONF-TR-531, RFC 6020, RFC 6087 and ONF TAPI UML model
                  <https://github.com/OpenNetworkingFoundation/TAPI/tree/v2.0.1/UML>";
    }
    revision 2018-01-02 {
        description "ONF Transport API version 2.0.0
        This YANG module has been generated from the TAPI UML Model using the IISOMI-Eagle xmi2yang mapping tool.
        Changes in this revision: <https://github.com/OpenNetworkingFoundation/TAPI/blob/develop/CHANGE_LOG/change-log.2.0.0.md>";
        reference "ONF-TR-527, ONF-TR-512, ONF-TR-531, RFC 6020, RFC 6087 and ONF TAPI UML model
                  <https://github.com/OpenNetworkingFoundation/TAPI/tree/v2.0.0/UML>";
    }
    augment "/tapi-common:context/tapi-notification:notification-context/tapi-notification:notification" {
        container alarm-info {
            uses alarm-info;
            description "none";
        }
        description "none";
    }
    augment "/tapi-common:context/tapi-notification:notification-context/tapi-notification:notification" {
        container tca-info {
            uses tca-info;
            description "none";
        }
        description "none";
    }
    /**************************
    * package object-classes
    **************************/ 
    grouping alarm-info {
        leaf alarm-identifier {
            type tapi-common:uuid;
            description "none";
        }
        leaf alarm-name {
            type alarm-condition-name;
            description "none";
        }
        leaf native-alarm-identifier {
            type string;
            description "none";
        }
        leaf native-alarm-info {
            type string;
            description "none";
        }
        leaf is-transient {
            type boolean;
            description "An alarm is transient when stateless, i.e. an explicit clear notification is not foreseen.";
        }
        leaf perceived-severity {
            type perceived-severity-type;
            description "The alarm severity.";
        }
        leaf probable-cause {
            type string;
            description "The alarm probable cause.";
        }
        leaf service-affecting {
            type service-affecting;
            description "The impact on the service.";
        }
        leaf alarm-category {
            type alarm-category;
            description "none";
        }
        list layer-info {
            uses layer-info;
            description "none";
        }
        container networking-alarm-info {
            uses networking-alarm-info;
            description "none";
        }
        container security-alarm-info {
            uses security-alalrm-info;
            description "none";
        }
        container alarm-tca-lifecycle {
            uses alarm-tca-lifecycle;
            description "none";
        }
        description "This class augments the Notification class with alarm related parameters.";
    }
    grouping tca-info {
        leaf tca-identifier {
            type tapi-common:uuid;
            description "none";
        }
        leaf threshold-indicator-name {
            type tapi-common:pm-parameter-name;
            description "none";
        }
        leaf is-transient {
            type boolean;
            description "A threshold crossing alert is transient when stateless, i.e. an explicit clear notification is not foreseen.";
        }
        leaf perceived-severity {
            type tapi-oam:perceived-tca-severity;
            description "The threshold crossing alert severity.";
        }
        container alarm-tca-lifecycle {
            uses alarm-tca-lifecycle;
            description "none";
        }
        container threshold-info {
            uses threshold-info;
            description "none";
        }
        description "This class augments the Notification class with threshold crossing alert related parameters.";
    }
    grouping threshold-info {
        container threshold-observed-value {
            uses tapi-common:pm-parameter-value;
            description "none";
        }
        leaf threshold-crossing {
            type threshold-crossing-type;
            description "none";
        }
        container threshold-configured-value {
            uses tapi-common:pm-parameter-value;
            description "none";
        }
        leaf threshold-units {
            type string;
            description "none";
        }
        container threshold-granularity {
            uses tapi-common:time-interval;
            description "none";
        }
        container measurement-interval {
            uses measurement-interval;
            description "The measurement interval time of the related PM metric.";
        }
        leaf suspect-interval-flag {
            type boolean;
            description "This attribute is used to indicate that the performance data for the current period may not be reliable. Some reasons for this to occur are:
                – Suspect data were detected by the actual resource doing data collection.
                – Transition of the administrativeState attribute to/from the 'lock' state.
                – Transition of the operationalState to/from the 'disabled' state.
                – Scheduler setting that inhibits the collection function.
                – The performance counters were reset during the interval.
                – The currentData (or subclass) object instance was created during the monitoring period.";
        }
        leaf oam-job {
            type tapi-common:uuid;
            description "Reference to the OamJob instance for which the PM metric and threshold values were configured.
                MEF 35.1: Identification of the PM Session for which the TCA Function was configured.";
        }
        description "none";
    }
    grouping alarm-tca-lifecycle {
        leaf alarm-tca-life-cycle {
            type alarm-tca-life-cycle;
            description "none";
        }
        leaf raised-time {
            type tapi-common:date-and-time;
            description "none";
        }
        leaf changed-time {
            type tapi-common:date-and-time;
            description "none";
        }
        leaf cleared-time {
            type tapi-common:date-and-time;
            description "none";
        }
        leaf occurrence-times {
            type uint64;
            description "none";
        }
        description "none";
    }

    /**************************
    * package type-definitions
    **************************/ 
    identity ALARM_CATEGORY {
        description "none";
    }
    identity ALARM_CATEGORY_EQUIPMENT {
        base ALARM_CATEGORY;
        description "none";
    }
    identity ALARM_CATEGORY_ENVIRONMENT {
        base ALARM_CATEGORY;
        description "none";
    }
    identity ALARM_CATEGORY_CONNECTIVITY {
        base ALARM_CATEGORY;
        description "none";
    }
    identity ALARM_CATEGORY_TCA {
        base ALARM_CATEGORY;
        description "none";
    }
    identity ALARM_CATEGORY_PROCESSING {
        base ALARM_CATEGORY;
        description "none";
    }
    identity ALARM_CATEGORY_SECURITY {
        base ALARM_CATEGORY;
        description "none";
    }
    identity THRESHOLD_CROSSING_TYPE {
        description "none";
    }
    identity THRESHOLD_CROSSING_TYPE_ABOVE {
        base THRESHOLD_CROSSING_TYPE;
        description "none";
    }
    identity THRESHOLD_CROSSING_TYPE_BELOW {
        base THRESHOLD_CROSSING_TYPE;
        description "none";
    }
    identity ALARM_TCA_LIFE_CYCLE {
        description "none";
    }
    identity ALARM_TCA_LIFE_CYCLE_ACTIVE {
        base ALARM_TCA_LIFE_CYCLE;
        description "none";
    }
    identity ALARM_TCA_LIFE_CYCLE_CLEAR {
        base ALARM_TCA_LIFE_CYCLE;
        description "none";
    }
    identity ALARM_CONDITION_NAME {
        description "none";
    }
    identity SECURITY_ALARM_CONDITION_NAME {
        description "none";
    }
    identity SECURITY_ALARM_CATEGORY {
        description "none";
    }
    identity PERCEIVED_TCA_SEVERITY {
        description "none";
    }
    identity PERCEIVED_TCA_SEVERITY_WARNING {
        base PERCEIVED_TCA_SEVERITY;
        description "ITU-T G.7710/X.733/M.3100: Indication for a potential or impending service-affecting fault. Further diagnosis should be made.";
    }
    identity PERCEIVED_TCA_SEVERITY_CLEAR {
        base PERCEIVED_TCA_SEVERITY;
        description "Included only for some possible backward compatibility purpose. It should not be used to assign a severity to a failure.
            ITU-T G.7710: The severities 'cleared' and 'indeterminate' defined by [ITU-T X.733] are not included in Table 2, as it is assumed that these are not to be used to assign a failure.";
    }
    identity ALARM_NOTIFICATION_TYPE {
        description "none";
    }
    identity ALARM_NOTIFICATION_TYPE_ALARM_EVENT {
        base ALARM_NOTIFICATION_TYPE;
        description "The notification of an alarm event.";
    }
    identity ALARM_NOTIFICATION_TYPE_THRESHOLD_CROSSING_ALERT {
        base ALARM_NOTIFICATION_TYPE;
        description "The notification of a threshold crossing alert event.";
    }
    grouping correlated-alarms {
        leaf correlated-alarm-identifier {
            type tapi-common:uuid;
            description "none";
        }
        leaf correlated-alarm-time-stamp {
            type tapi-common:date-and-time;
            description "none";
        }
        leaf correlated-alarm-name {
            type string;
            description "none";
        }
        description "none";
    }
    grouping networking-alarm-info {
        leaf root-cause-alarm {
            type boolean;
            description "none";
        }
        list correlated-alarms {
            key 'correlated-alarm-identifier';
            uses correlated-alarms;
            description "none";
        }
        list alarm-affected-services {
            key 'connectivity-service-identifier';
            uses alarm-affected-services;
            description "none";
        }
        description "none";
    }
    grouping alarm-affected-services {
        leaf connectivity-service-identifier {
            type tapi-common:uuid;
            description "none";
        }
        leaf connectivity-services-name {
            type string;
            description "none";
        }
        leaf connectivity-service-admin-status {
            type tapi-common:administrative-state;
            description "none";
        }
        description "none";
    }
    grouping security-alalrm-info {
        leaf security-alarm-cause {
            type security-alarm-condition-name;
            description "none";
        }
        leaf security-alarm-severity {
            type tapi-oam:perceived-severity-type;
            description "none";
        }
        leaf security-alarm-category {
            type security-alarm-category;
            description "none";
        }
        leaf security-alarm-detector {
            type string;
            description "none";
        }
        leaf security-service-user {
            type string;
            description "none";
        }
        leaf security-service-provider {
            type string;
            description "none";
        }
        description "none";
    }
    typedef alarm-category {
        type identityref {
            base ALARM_CATEGORY;
        }
        description "none";
    }
    grouping measurement-interval {
        leaf begin-time {
            type tapi-common:date-and-time;
            description "none";
        }
        leaf end-time {
            type tapi-common:date-and-time;
            description "none";
        }
        description "none";
    }
    typedef threshold-crossing-type {
        type identityref {
            base THRESHOLD_CROSSING_TYPE;
        }
        description "none";
    }
    typedef alarm-tca-life-cycle {
        type identityref {
            base ALARM_TCA_LIFE_CYCLE;
        }
        description "none";
    }
    typedef perceived-severity-type {
        type enumeration {
            enum CRITICAL {
                description "ITU-T G.7710/X.733/M.3100: Indication for a service-affecting condition. Immediate corrective action is required.";
            }
            enum MAJOR {
                description "ITU-T G.7710/X.733/M.3100: Indication for a service-affecting condition. Urgent corrective action is required.";
            }
            enum MINOR {
                description "ITU-T G.7710/X.733/M.3100: Indication for a non-service-affecting condition. Corrective action should be taken in order to prevent more serious fault.";
            }
            enum WARNING {
                description "ITU-T G.7710/X.733/M.3100: Indication for a potential or impending service-affecting fault. Further diagnosis should be made.";
            }
            enum CLEARED {
                description "Included only for some possible backward compatibility purpose. It should not be used to assign a severity to a failure.
                    ITU-T G.7710: The severities 'cleared' and 'indeterminate' defined by [ITU-T X.733] are not included in Table 2, as it is assumed that these are not to be used to assign a failure.";
            }
        }
        description "The types of perceived severity.
            ITU-T G.7710: Failures may have been categorized to indicate the severity or urgency of the fault.";
    }
    typedef service-affecting {
        type enumeration {
            enum SERVICE_AFFECTING {
                description "The service is affected by the failure.";
            }
            enum NOT_SERVICE_AFFECTING {
                description "The service is not affected by the failure.";
            }
            enum UNKNOWN {
                description "The impact on the service is unknown.";
            }
        }
        description "The possible impact on the service.";
    }
    typedef alarm-condition-name {
        type identityref {
            base ALARM_CONDITION_NAME;
        }
        description "The alarm condition name, or alarm probable cause.
            This extensible enumeration can be augmented with specific alarm condition names in the other modules.";
    }
    typedef security-alarm-condition-name {
        type identityref {
            base SECURITY_ALARM_CONDITION_NAME;
        }
        description "The security alarm condition name, or alarm probable cause.";
    }
    typedef security-alarm-category {
        type identityref {
            base SECURITY_ALARM_CATEGORY;
        }
        description "none";
    }
    typedef threshold-crossing-qualifier {
        type enumeration {
            enum NOT_APPLICABLE {
                description "Location or qualifier not applicable.";
            }
            enum NEAR_END {
                description "Near End detection.";
            }
            enum FAR_END {
                description "Far end detection.";
            }
            enum BIDIRECTIONAL {
                description "Composition of near and far end detections.";
            }
            enum FORWARD {
                description "MEF 35.1: The direction of performance measurements from the Controller MEP towards the Responder or Sink MEP, when One-way measurements are taken using a Single-Ended or Dual-Ended PM Function.
                    MEF 83: In Single-Ended measurements, it is assumed that the the FORWARD and FAR_END qualifiers are equivalent.
                    In Dual-Ended measurements (and in case of TX counters), it is assumed that the FORWARD and NEAR_END qualifiers are equivalent.";
            }
            enum BACKWARD {
                description "MEF 35.1: The direction of performance measurements from the Responder MEP towards the Controller MEP, when One-way measurements are taken using a Single-Ended PM Function.
                    Note: this term is not applicable when Dual-Ended PM Functions are used.
                    MEF 83: In Single-Ended measurements, it is assumed that the BACKWARD and NEAR_END qualifiers are equivalent.
                    In Dual-Ended measurements (and in case of TX counters), it is assumed that the BACKWARD and FAR_END qualifiers are equivalent.";
            }
        }
        description "Threshold crossing location or qualifier.";
    }
    typedef perceived-tca-severity {
        type identityref {
            base PERCEIVED_TCA_SEVERITY;
        }
        description "The types of perceived severity of threshold crossing alerts.";
    }
    typedef alarm-notification-type {
        type identityref {
            base ALARM_NOTIFICATION_TYPE;
        }
        description "The list of alarm specific notification types.";
    }
    grouping layer-info {
        leaf layer-protocol-name {
            type tapi-common:layer-protocol-name;
            description "none";
        }
        leaf layer-protocol-qualifier {
            type tapi-common:layer-protocol-qualifier;
            description "none";
        }
        description "none";
    }

}
