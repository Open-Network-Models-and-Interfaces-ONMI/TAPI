module TapiNotification {
    namespace "urn:onf:params:xml:ns:yang:TapiNotification";
    prefix TapiNotification;
    import Tapi {
        prefix Tapi;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-07-21 {
        description "Latest revision";
        reference "RFC 6020 and RFC 6087";
    }
    augment "/Tapi:Context/Tapi:_notifSubscription" {
        uses NotificationSubscriptionService;
        description "none";
    }
    augment "/Tapi:Context/Tapi:_notification" {
        uses Notification;
        description "none";
    }
    /***********************
    * package ObjectClasses
    **********************/ 
        grouping NotificationSubscriptionService {
            list _notification {
                key 'uuid';
                config false;
                uses Notification;
                description "none";
            }
            container _notificationChannel {
                uses NotificationChannel;
                description "none";
            }
            container _subscriptionFilter {
                uses SubscriptionFilter;
                description "none";
            }
            leaf subscriptionState {
                type SubscriptionState;
                description "none";
            }
            leaf-list supportedNotificationTypes {
                type NotificationType;
                config false;
                description "none";
            }
            leaf-list supportedObjectTypes {
                type ObjectType;
                config false;
                description "none";
            }
            uses Tapi:ServiceSpec;
            description "none";
        }
        grouping SubscriptionFilter {
            leaf-list requestedNotificationTypes {
                type NotificationType;
                config false;
                description "none";
            }
            leaf-list requestedObjectTypes {
                type ObjectType;
                config false;
                description "none";
            }
            leaf-list requestedLayerProtocols {
                type Tapi:LayerProtocolName;
                config false;
                description "none";
            }
            leaf-list requestedObjectIdentifier {
                type Tapi:UniversalId;
                config false;
                description "none";
            }
            leaf includeContent {
                type boolean;
                config false;
                description "Indicates whether the published Notification includes content or just the Notification Id (which enables retrieval of the notification at the later stage)";
            }
            description "none";
        }
        notification Notification {
            uses Notification;
            description "none";
        }
        grouping Notification {
            leaf notificationType {
                type NotificationType;
                description "none";
            }
            leaf targetObjectType {
                type ObjectType;
                description "none";
            }
            leaf targetObjectIdentifier {
                type Tapi:UniversalId;
                description "none";
            }
            list targetObjectName {
                key 'valueName';
                uses Tapi:NameAndValue;
                description "none";
            }
            leaf eventTimeStamp {
                type Tapi:DateAndTime;
                description "none";
            }
            leaf sequenceNumber {
                type uint64;
                config false;
                description "A monotonous increasing sequence number associated with the notification.
                    The exact semantics of how this sequence number is assigned (per channel or subscription or source or system) is left undefined.";
            }
            leaf sourceIndicator {
                type SourceIndicator;
                description "none";
            }
            leaf layerProtocolName {
                type Tapi:LayerProtocolName;
                description "none";
            }
            list changedAttributes {
                uses NameAndValueChange;
                description "none";
            }
            list additionalInfo {
                key 'valueName';
                uses Tapi:NameAndValue;
                description "none";
            }
            leaf additionalText {
                type string;
                description "none";
            }
            uses Tapi:ResourceSpec;
            description "none";
        }
        grouping NotificationChannel {
            leaf streamAddress {
                type string;
                config false;
                description "The address/location/URI of the channel/stream to which the subscribed notifications are published.
                    This specifics of this is typically dependent on the implementation protocol & mechanism and hence is typed as a string.";
            }
            leaf nextSequenceNo {
                type uint64;
                config false;
                description "The sequence number of the next notification that will be published on the channel";
            }
            description "none";
        }
    
    /***********************
    * package TypeDefinitions
    **********************/ 
        grouping NameAndValueChange {
            leaf valueName {
                type string;
                description "The name of the value. The value need not have a name.";
            }
            leaf oldValue {
                type string;
                description "The value";
            }
            leaf newValue {
                type string;
                description "The value";
            }
            description "A scoped name-value triple, including old value and new value";
        }
        typedef NotificationType {
            type enumeration {
                enum OBJECT_CREATION {
                    description "Not a normal state. The system is unable to determine the correct value.";
                }
                enum OBJECT_DELETION {
                    description "none";
                }
                enum ATTRIBUTE_VALUE_CHANGE {
                    description "none";
                }
            }
            description "The orientation of flow at the Port of a Forwarding entity";
        }
        typedef ObjectType {
            type enumeration {
                enum TOPOLOGY {
                    description "none";
                }
                enum NODE {
                    description "none";
                }
                enum LINK {
                    description "none";
                }
                enum CONNECTION {
                    description "none";
                }
                enum PATH {
                    description "none";
                }
                enum CONNECTIVITY_SERVICE {
                    description "none";
                }
                enum VIRTUAL_NETWORK_SERVICE {
                    description "none";
                }
                enum PATH_COMPUTATION_SERVICE {
                    description "none";
                }
                enum NODE_EDGE_POINT {
                    description "none";
                }
                enum SERVICE_END_POINT {
                    description "none";
                }
                enum CONNECTION_END_POINT {
                    description "none";
                }
            }
            description "The orientation of flow at the Port of a Forwarding entity";
        }
        typedef SourceIndicator {
            type enumeration {
                enum RESOURCE_OPERATION {
                    description "none";
                }
                enum MANAGEMENT_OPERATION {
                    description "none";
                }
                enum UNKNOWN {
                    description "none";
                }
            }
            description "none";
        }
        typedef SubscriptionState {
            type enumeration {
                enum SUSPENDED {
                    description "none";
                }
                enum ACTIVE {
                    description "none";
                }
            }
            description "none";
        }
    
    /***********************
    * package Interfaces
    **********************/ 
        rpc getSupportedNotificationTypes {
            description "none";
            output {
                leaf-list supportedNotificationTypes {
                    type NotificationType;
                    min-elements 1;
                    description "none";
                }
                leaf-list supportedObjectTypes {
                    type ObjectType;
                    min-elements 1;
                    description "none";
                }
            }
        }
        rpc createNotificationSubscriptionService {
            description "none";
            input {
                container subscriptionFilter {
                    uses SubscriptionFilter;
                    description "none";
                }
                leaf subscriptionState {
                    type SubscriptionState;
                    description "none";
                }
            }
            output {
                container subscriptionService {
                    uses NotificationSubscriptionService;
                    description "none";
                }
            }
        }
        rpc updateNotificationSubscriptionService {
            description "none";
            input {
                leaf subscriptionIdOrName {
                    type string;
                    description "none";
                }
                container subscriptionFilter {
                    uses SubscriptionFilter;
                    description "none";
                }
                leaf subscriptionState {
                    type SubscriptionState;
                    description "none";
                }
            }
            output {
                container subscriptionService {
                    uses NotificationSubscriptionService;
                    description "none";
                }
            }
        }
        rpc deleteNotificationSubscriptionService {
            description "none";
            input {
                leaf subscriptionIdOrName {
                    type string;
                    description "none";
                }
            }
            output {
                container subscriptionService {
                    uses NotificationSubscriptionService;
                    description "none";
                }
            }
        }
        rpc getNotificationSubscriptionServiceDetails {
            description "none";
            input {
                leaf subscriptionIdOrName {
                    type string;
                    description "none";
                }
            }
            output {
                container subscriptionService {
                    uses NotificationSubscriptionService;
                    description "none";
                }
            }
        }
        rpc getNotificationSubscriptionServiceList {
            description "none";
            output {
                list subscriptionService {
                    uses NotificationSubscriptionService;
                    description "none";
                }
            }
        }
        rpc getNotificationList {
            description "none";
            input {
                leaf subscriptionIdOrName {
                    type string;
                    description "none";
                }
                leaf timePeriod {
                    type string;
                    description "none";
                }
            }
            output {
                list notification {
                    uses Notification;
                    description "none";
                }
            }
        }
    
}
