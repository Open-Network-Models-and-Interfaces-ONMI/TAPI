module Tapi-Interfaces-ConnectivityService {
    namespace "urn:ONF:Tapi-Interfaces-ConnectivityService";
    prefix Tapi-Interfaces-ConnectivityService;
    import Tapi-ObjectClasses {
        prefix Tapi-ObjectClasses;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-08 {
        description "Latest revision";
        reference "RFC 6020 and RFC 6087";
    }
    rpc getConnectionDetails {
        description "none";
        input {
            leaf serviceIdOrName {
                type string;
                description "none";
            }
            leaf connectionIdOrName {
                type string;
                description "none";
            }
        }
        output {
            container connection {
                uses Tapi-ObjectClasses:Connection;
                description "none";
            }
        }
    }
    rpc getConnectivityServiceList {
        description "none";
        output {
            list connService {
                uses Tapi-ObjectClasses:ConnectivityService;
                description "none";
            }
        }
    }
    rpc getConnectionEndPointDetails {
        description "none";
        input {
            leaf serviceIdOrName {
                type string;
                description "none";
            }
            leaf connectionIdOrName {
                type string;
                description "none";
            }
            leaf connEPIdOrName {
                type string;
                description "none";
            }
        }
        output {
            container connEP {
                uses Tapi-ObjectClasses:ConnectionEndPoint;
                description "none";
            }
        }
    }
    rpc getServiceEndPointDetails {
        description "none";
        input {
            leaf serviceEPIdOrName {
                type string;
                description "none";
            }
        }
        output {
            container serviceEndPoint {
                uses Tapi-ObjectClasses:ServiceEndPoint;
                description "none";
            }
        }
    }
    rpc getConnectivityServiceDetails {
        description "none";
        input {
            leaf serviceIdOrName {
                type string;
                description "none";
            }
        }
        output {
            container connService {
                uses Tapi-ObjectClasses:ConnectivityService;
                description "none";
            }
        }
    }
    rpc getServiceEndPointList {
        description "none";
        output {
            list serviceEndPoint {
                uses Tapi-ObjectClasses:ServiceEndPoint;
                description "none";
            }
        }
    }
    rpc createConnectivityService {
        description "none";
        input {
            list servicePort {
                min-elements 2;
                uses Tapi-ObjectClasses:ConnectivityServicePort;
                description "none";
            }
            container connConstraint {
                uses Tapi-ObjectClasses:ConnectivityConstraint;
                description "none";
            }
            container connSchedule {
                uses Tapi-ObjectClasses:TimeRange;
                description "none";
            }
        }
        output {
            container connService {
                uses Tapi-ObjectClasses:ConnectivityService;
                description "none";
            }
        }
    }
    rpc updateConnectivityService {
        description "none";
        input {
            leaf serviceIdOrName {
                type string;
                description "none";
            }
            container connConstraint {
                uses Tapi-ObjectClasses:ConnectivityConstraint;
                description "none";
            }
            container connSchedule {
                uses Tapi-ObjectClasses:TimeRange;
                description "none";
            }
        }
        output {
            container connService {
                uses Tapi-ObjectClasses:ConnectivityService;
                description "none";
            }
        }
    }
    rpc deleteConnectivityService {
        description "none";
        input {
            leaf serviceIdOrName {
                type string;
                description "none";
            }
        }
        output {
            container connService {
                uses Tapi-ObjectClasses:ConnectivityService;
                description "none";
            }
        }
    }
}
