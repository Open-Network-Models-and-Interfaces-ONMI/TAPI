module Tapi {
    namespace "urn:onf:params:xml:ns:yang:Tapi";
    prefix Tapi;
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-09-14 {
        description "Latest revision";
        reference "RFC 6020 and RFC 6087";
    }
    augment "/Tapi:Context/Tapi:_serviceEndPoint" {
        uses ServiceEndPoint;
        description "none";
    }
    /***********************
    * package ObjectClasses
    **********************/ 
        grouping AdminStatePac {
            leaf administrativeState {
                type AdministrativeState;
                description "none";
            }
            leaf operationalState {
                type OperationalState;
                description "none";
            }
            leaf lifecycleState {
                type LifecycleState;
                description "none";
            }
            description "Provides state attributes that are applicable to an entity that can be administered. Such an entity also has operational and lifecycle aspects.";
        }
        grouping GlobalClass {
            leaf uuid {
                type UniversalId;
                description "UUID: An identifier that is universally unique
                    (consider in the context of Identifier: A property of an entity/role with a value that is unique within an identifier space, where the identifier space is itself globally unique, and immutable. An identifier carries no semantics with respect to the purpose or state of the entity)";
            }
            list name {
                key 'valueName';
                uses NameAndValue;
                description "List of names. A property of an entity with a value that is unique in some namespace but may change during the life of the entity. A name carries no semantics with respect to the purpose of the entity.";
            }
            list label {
                key 'valueName';
                uses NameAndValue;
                description "List of labels.A property of an entity with a value that is not expected to be unique and is allowed to change. A label carries no semantics with respect to the purpose of the entity and has no effect on the entity behavior or state.";
            }
            list _extensions {
                key 'extensionsSpecification';
                config false;
                uses ExtensionsSpec;
                description "none";
            }
            description "The TAPI GlobalComponent serves as the super class for all TAPI entities that can be directly retrieved by their ID. As such, these are first class entities and their ID is expected to be globally unique. ";
        }
        grouping LayerProtocol {
            leaf layerProtocolName {
                type LayerProtocolName;
                description "Indicate the specific layer-protocol described by the LayerProtocol entity.";
            }
            leaf terminationDirection {
                type TerminationDirection;
                description "The overall directionality of the LP. 
                    - A BIDIRECTIONAL LP will have some SINK and/or SOURCE flowss.
                    - A SINK LP can only contain elements with SINK flows or CONTRA_DIRECTION_SOURCE flows
                    - A SOURCE LP can only contain SOURCE flows or CONTRA_DIRECTION_SINK flows";
            }
            leaf terminationState {
                type TerminationState;
                description "Indicates whether the layer is terminated and if so how.";
            }
            uses LocalClass;
            description "Each transport layer is represented by a LayerProtocol (LP) instance. The LayerProtocol instances it can be used for controlling termination and monitoring functionality. 
                It can also be used for controlling the adaptation (i.e. encapsulation and/or multiplexing of client signal), tandem connection monitoring, traffic conditioning and/or shaping functionality at an intermediate point along a connection. 
                Where the client – server relationship is fixed 1:1 and immutable, the layers can be encapsulated in a single LTP instance. Where the is a n:1 relationship between client and server, the layers must be split over two separate instances of LTP. ";
        }
        grouping LifecycleStatePac {
            leaf lifecycleState {
                type LifecycleState;
                description "none";
            }
            description "Provides state attributes for an entity that has lifeccycle aspects only.";
        }
        grouping LocalClass {
            leaf localId {
                type string;
                description "none";
            }
            list name {
                key 'valueName';
                uses NameAndValue;
                description "List of names. A property of an entity with a value that is unique in some namespace but may change during the life of the entity. A name carries no semantics with respect to the purpose of the entity.";
            }
            list _extensions {
                key 'extensionsSpecification';
                config false;
                uses ExtensionsSpec;
                description "none";
            }
            description "The TAPI GlobalComponent serves as the super class for all TAPI entities that can be directly retrieved by their ID. As such, these are first class entities and their ID is expected to be globally unique. ";
        }
        grouping OperationalStatePac {
            leaf operationalState {
                type OperationalState;
                description "none";
            }
            leaf lifecycleState {
                type LifecycleState;
                description "none";
            }
            description "Provides state attributes that are applicable to an entity that reflects operational aspects. Such an entity is expected to also have lifecycle aspects.";
        }
        grouping TimeRange {
            leaf endTime {
                type DateAndTime;
                description "none";
            }
            leaf startTime {
                type DateAndTime;
                description "none";
            }
            description "none";
        }
        grouping ExtensionsSpec {
            leaf extensionsSpecification {
                type string;
                config false;
                description "none";
            }
            leaf-list extensionsSpecTarget {
                type string;
                config false;
                min-elements 0;
                description "none";
            }
            description "none";
        }
        grouping Context {
            container _nwTopologyService {
                presence "Context is available";
                config false;
                uses ServiceSpec;
                description "none";
            }
            list _connectivityService {             
                key 'uuid';
                uses ServiceSpec;
                description "none";
            }
            list _vnwService {
                key 'uuid';
                uses ServiceSpec;
                description "none";
            }
            list _pathCompService {
                key 'uuid';
                uses ServiceSpec;
                description "none";
            }
            list _notifSubscription {
                key 'uuid';
                uses ServiceSpec;
                description "none";
            }
            list _serviceEndPoint {
                key 'uuid';
                config false;
                uses ResourceSpec;
                description "none";
            }
            list _topology {
                key 'uuid';
                config false;
                uses ResourceSpec;
                description "none";
            }
            list _connection {
                key 'uuid';
                config false;
                uses ResourceSpec;
                description "none";
            }
            list _path {
                key 'uuid';
                config false;
                uses ResourceSpec;
                description "none";
            }
            list _notification {
                key 'uuid';
                config false;
                uses ResourceSpec;
                description "none";
            }
            uses GlobalClass;
            description "The Network Control Domain (NCD) object class represents the scope of control that a particular SDN controller has with respect to a particular network, (i.e., encompassing a designated set of interconnected (virtual) network elements).";
        }
        container Context {
            presence "Context is available";
            uses Context;
            description "none";        
        }
        grouping ResourceSpec {
            uses GlobalClass;
            description "none";
        }
        grouping ServiceSpec {
            uses GlobalClass;
            description "none";
        }
        grouping ServiceEndPoint {
            list _layerProtocol {
                key 'localId';
                config false;
                min-elements 1;
                uses LayerProtocol;
                description "none";
            }
            container _state {
                config false;
                uses LifecycleStatePac;
                description "none";
            }
            leaf direction {
                type TerminationDirection;
                config false;
                description "none";
            }
            //uses ResourceSpec;
            description "The LogicalTerminationPoint (LTP) object class encapsulates the termination and adaptation functions of one or more transport layers. 
                The structure of LTP supports all transport protocols including circuit and packet forms.";
        }
    
    /***********************
    * package TypeDefinitions
    **********************/ 
        typedef AdministrativeState {
            type enumeration {
                enum LOCKED {
                    description "Users are administratively prohibited from making use of the resource.";
                }
                enum UNLOCKED {
                    description "Users are allowed to use the resource";
                }
            }
            description "The possible values of the administrativeState.";
        }
        typedef DateAndTime {
            type string;
            description "This primitive type defines the date and time according to the following structure:
                yyyyMMddhhmmss.s[Z|{+|-}HHMm] where:
                yyyy    0000..9999    year
                MM    01..12            month
                dd        01..31            day
                hh        00..23            hour
                mm    00..59            minute
                ss        00..59            second
                s        .0...9            tenth of second (set to .0 if EMS or NE cannot support this granularity)
                Z        Z                indicates UTC (rather than local time)
                {+|-}    + or -            delta from UTC
                HH        00..23            time zone difference in hours
                Mm    00..59            time zone difference in minutes.";
        }
        typedef DirectiveValue {
            type enumeration {
                enum MINIMIZE {
                    description "none";
                }
                enum MAXIMIZE {
                    description "none";
                }
                enum ALLOW {
                    description "none";
                }
                enum DISALLOW {
                    description "none";
                }
                enum DONT_CARE {
                    description "none";
                }
            }
            description "none";
        }
        typedef ForwardingDirection {
            type enumeration {
                enum BIDIRECTIONAL {
                    description "The Fowarding entity supports both BIDIRECTIONAL flows at all Ports (i.e. all Ports have both an INPUT flow and an OUTPUT flow defined)";
                }
                enum UNIDIRECTIONAL {
                    description "The Forwarding entity has Ports that are either INPUT or OUTPUT. It has no BIDIRECTIONAL Ports.";
                }
                enum UNDEFINED_OR_UNKNOWN {
                    description "Not a normal state. The system is unable to determine the correct value.";
                }
            }
            description "The directionality of a Forwarding entity.";
        }
        typedef LayerProtocolName {
            type enumeration {
                enum OCH {
                    description "none";
                }
                enum ODU {
                    description "none";
                }
                enum ETH {
                    description "none";
                }
                enum MPLS_TP {
                    description "none";
                }
            }
            description "Provides a controlled list of layer protocol names and indicates the naming authority.
                Note that it is expected that attributes will be added to this structure to convey the naming authority name, the name of the layer protocol using a human readable string and any particular standard reference.
                Layer protocol names include:
                -    Layer 1 (L1): OTU, ODU
                -    Layer 2 (L2): Carrier Grade Ethernet (ETY, ETH), MPLS-TP (MT)
                ";
        }
        typedef LifecycleState {
            type enumeration {
                enum PLANNED {
                    description "The resource is planned but is not present in the network.";
                }
                enum POTENTIAL {
                    description "The supporting resources are present in the network but are shared with other clients; or require further configuration before they can be used; or both.
                        o    When a potential resource is configured and allocated to a client it is moved to the “installed” state for that client.
                        o    If the potential resource has been consumed (e.g. allocated to another client) it is moved to the “planned” state for all other clients.";
                }
                enum INSTALLED {
                    description "The resource is present in the network and is capable of providing the service expected.";
                }
                enum RESTORING {
                    description "The resource is resilient and is performing a restoration operation.";
                }
                enum PENDING_REMOVAL {
                    description "The resource has been marked for removal";
                }
            }
            description "The possible values of the lifecycleState.";
        }
        grouping NameAndValue {
            leaf valueName {
                type string;
                description "The name of the value. The value need not have a name.";
            }
            leaf value {
                type string;
                description "The value";
            }
            description "A scoped name-value pair";
        }
        typedef OperationalState {
            type enumeration {
                enum DISABLED {
                    description "The resource is unable to meet the SLA of the user of the resource. If no (explicit) SLA is defined the resource is disabled if it is totally inoperable and unable to provide service to the user.";
                }
                enum ENABLED {
                    description "The resource is partially or fully operable and available for use";
                }
            }
            description "The possible values of the operationalState.";
        }
        typedef PortDirection {
            type enumeration {
                enum BIDIRECTIONAL {
                    description "The Port has both an INPUT flow and an OUTPUT flow defined.";
                }
                enum INPUT {
                    description "The Port only has definition for a flow into the Forwarding entity (i.e. an ingress flow).";
                }
                enum OUTPUT {
                    description "The Port only has definition for a flow out of the Forwarding entity (i.e. an egress flow).";
                }
                enum UNIDENTIFIED_OR_UNKNOWN {
                    description "Not a normal state. The system is unable to determine the correct value.";
                }
            }
            description "The orientation of flow at the Port of a Forwarding entity";
        }
        typedef PortRole {
            type enumeration {
                enum SYMMETRIC {
                    description "none";
                }
                enum ROOT {
                    description "none";
                }
                enum LEAF {
                    description "none";
                }
                enum UNKNOWN {
                    description "none";
                }
            }
            description "The role of an end in the context of the function of the forwarding entity that it bounds";
        }
        typedef TerminationDirection {
            type enumeration {
                enum BIDIRECTIONAL {
                    description "A Termination with both SINK and SOURCE flows.";
                }
                enum SINK {
                    description "The flow is up the layer stack from the server side to the client side. 
                        Considering an example of a Termination function within the termination entity, a SINK flow:
                        - will arrive at at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termiation can be bound to an OUTPUT Port of a Forwarding entity";
                }
                enum SOURCE {
                    description "The flow is down the layer stack from the server side to the client side. 
                        Considering an example of a Termination function within the termination entity, a SOURCE flow:
                        - will arrive at at the top of the termination function (the client side) where it is essentially at an INPUT to the termination component
                        - then will be assembled with various overheads etc and will be coded 
                        - then coded form of the assembly of flow will be sent out of the termination function (the server side) where it is essentially at an OUTPUT from the termination component
                        A SOURCE termination is one that only supports a SOURCE flow.
                        A SOURCE termiation can be bound to an INPUT Port of a Forwarding entity";
                }
                enum UNDEFINED_OR_UNKNOWN {
                    description "Not a normal state. The system is unable to determine the correct value.";
                }
            }
            description "The directionality of a termination entity";
        }
        typedef TerminationState {
            type enumeration {
                enum LP_CAN_NEVER_TERMINATE {
                    description "A non-flexible case that can never be terminated.";
                }
                enum LT_NOT_TERMINATED {
                    description "A flexible termination that can terminate but is currently not terminated.";
                }
                enum TERMINATED_SERVER_TO_CLIENT_FLOW {
                    description "A flexible termination that is currently terminated for server to client flow only.";
                }
                enum TERMINATED_CLIENT_TO_SERVER_FLOW {
                    description "A flexible termination that is currently terminated for client to server flow only.";
                }
                enum TERMINATED_BIDIRECTIONAL {
                    description "A flexible termination that is currently terminated in both directions of flow.";
                }
                enum LT_PERMENANTLY_TERMINATED {
                    description "A non-flexible termination that is always terminated (in both directions of flow for a bidirectional case and in the one direction of flow for both unidirectional cases).";
                }
                enum TERMINATION_STATE_UNKNOWN {
                    description "There TerminationState cannot be determined.";
                }
            }
            description "Provides support for the range of behaviours and specific states that an LP can take with respect to termination of the signal.
                Indicates to what degree the LayerTermination is terminated.";
        }
        typedef UniversalId {
            type string {
                pattern '[0-9a-fA-F]{8}-[0-9a-fA-F]{4}-[0-9a-fA-F]{4}-' + '[0-9a-fA-F]{4}-[0-9a-fA-F]{12}';
            }
           description
            "A Universally Unique IDentifier in the string representation
             defined in RFC 4122.  The canonical representation uses
             lowercase characters.
    
             The following is an example of a UUID in string representation:
             f81d4fae-7dec-11d0-a765-00a0c91e6bf6
             ";
           reference
            "RFC 4122: A Universally Unique IDentifier (UUID) URN
                       Namespace";
       }
    
    /***********************
    * package Interfaces
    **********************/ 
        rpc getServiceEndPointDetails {
            description "none";
            input {
                leaf serviceEPIdOrName {
                    type string;
                    description "none";
                }
            }
            output {
                container serviceEndPoint {
                    uses ServiceEndPoint;
                    description "none";
                }
            }
        }
        rpc getServiceEndPointList {
            description "none";
            output {
                list serviceEndPoint {
                    uses ServiceEndPoint;
                    description "none";
                }
            }
        }
    
}
