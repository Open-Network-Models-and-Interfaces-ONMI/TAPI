module tapi-virtual-network {
    yang-version "1.1";
    namespace "urn:onf:otcc:yang:tapi-virtual-network";
    prefix tapi-virtual-network;
    import tapi-topology {
        prefix tapi-topology;
    }
    import tapi-common {
        prefix tapi-common;
    }
    import tapi-notification {
        prefix tapi-notification;
    }
    import tapi-streaming {
        prefix tapi-streaming;
    }
    organization "Linux Foundation ONMI (Open Network Modeling and Interfaces) Project";
    contact "
         Project Web: <https://github.com/Open-Network-Models-and-Interfaces-ONMI/onmi-home/wiki>
         Project List: <mailto:onmi-tapi@googlegroups.com>
         Editor: Nigel Davis <mailto:ndavis@ciena.com>
         Arturo Mayoral <mailto:amayoral@telecominfraproject.com>
         Ramon Casellas <mailto:ramon.casellas@cttc.es>";
    description "
        This module contains TAPI Virtual Network Model definitions.
        Source: TapiVirtualNetwork.uml
        - The TAPI YANG models included in this TAPI release are a *normative* part of the TAPI SDK.
        - The YANG specifications have been generated from the corresponding UML model using the [EAGLE UML2YANG mapping tool]
        <https://github.com/Open-Network-Models-and-Interfaces-ONMI/onmi-iisomi-uml-yang>
        and further edited manually to comply with the [ONMI IISOMI UML2YANG mapping guidelines]
        <https://github.com/Open-Network-Models-and-Interfaces-ONMI/onmi-iisomi-home>
        - Status of YANG model artifacts can be determined by referring to the corresponding UML artifacts.
        As described in the UML models, some artifacts are considered *experimental*, and thus the corresponding YANG artifacts.
        - The LF ONMI TAPI release process does not guarantee backward compatibility of YANG models across major versions of TAPI releases.
        The YANG model backward compatibility criteria are outlined in section 11 of <https://tools.ietf.org/html/rfc7950>.
        YANG models included in this release may not be backward compatible with some previous TAPI releases.
        - Previous revisions can now be found at https://github.com/Open-Network-Models-and-Interfaces-ONMI/TAPI under the 
        appropriate tag and, where relevant, fixes to those revisions can be found under the corresponding branches. The documentation for
        each significant revision is found at https://github.com/Open-Network-Models-and-Interfaces-ONMI/TAPI-Documentation under the
        appropriate tag and, where relevant, fixes to those revisions can be found under the corresponding branches.
        License: This module is distributed under the Apache License 2.0.";
    revision 2025-12-31 {
        description "LF ONMI Transport API version 2.5.2
                   Changes included in this TAPI release (v2.5.2) are listed in
                   <https://github.com/Open-Network-Models-and-Interfaces-ONMI/TAPI-Documentation/tree/v2.5.2/DeltaDocument>";
        reference "ONF-TR-527, ONF-TR-512, ONF-TR-531, RFC 7950, RFC 6087 and LF ONMI TAPI UML model
                  <https://github.com/Open-Network-Models-and-Interfaces-ONMI/TAPI/tree/v2.5.2/UML>";
    }
    revision 2023-10-10 {
        description "ONF Transport API version 2.5.0.
                   Changes included in this TAPI release (v2.5.0) are listed in
                   <https://wiki.opennetworking.org/display/OTCC/TAPI+Roadmap+2023>";
        reference "ONF-TR-527, ONF-TR-512, ONF-TR-531, RFC 7950, RFC 6087 and ONF TAPI UML model
                  <https://github.com/OpenNetworkingFoundation/TAPI/tree/v2.5.0/UML>";
    }
    revision 2023-03-21 {
        description "ONF Transport API version 2.4.1.
                   Changes included in this TAPI release (v2.4.1) are listed in
                   <https://wiki.opennetworking.org/display/OTCC/TAPI+Roadmap+2023>";
        reference "ONF-TR-527, ONF-TR-512, ONF-TR-531, RFC 7950, RFC 6087 and ONF TAPI UML model
                  <https://github.com/OpenNetworkingFoundation/TAPI/tree/v2.4.1/UML>";
    }
    revision 2022-12-22 {
        description "ONF Transport API version 2.4.0.
                   Changes included in this TAPI release (v2.4.0) are listed in
                   <https://wiki.opennetworking.org/display/OTCC/TAPI+Roadmap+2023>";
        reference "ONF-TR-527, ONF-TR-512, ONF-TR-531, RFC 7950, RFC 6087 and ONF TAPI UML model
                  <https://github.com/OpenNetworkingFoundation/TAPI/tree/v2.4.0/UML>";
    }
    revision 2022-11-21 {
        description "ONF Transport API version 2.4.0 RC1.
                   Changes included in this TAPI release (v2.4.0) are listed in
                   <https://wiki.opennetworking.org/display/OTCC/TAPI+Roadmap+2023>";
        reference "ONF-TR-527, ONF-TR-512, ONF-TR-531, RFC 7950, RFC 6087 and ONF TAPI UML model
                  <https://github.com/OpenNetworkingFoundation/TAPI/tree/v2.4.0-RC1/UML>";
    }
    revision 2021-09-24 {
        description "ONF Transport API version 2.3.1.
                   Changes included in this TAPI release (v2.3.1) are listed in
                   <https://wiki.opennetworking.org/display/OTCC/Archived+Deliveries>";
        reference "ONF-TR-527, ONF-TR-512, ONF-TR-531, RFC 7950, RFC 6087 and ONF TAPI UML model
                  <https://github.com/OpenNetworkingFoundation/TAPI/tree/v2.3.1/UML>";
    }
    revision 2021-08-04 {
        description "ONF Transport API version 2.3.
                   Changes included in this TAPI release (v2.3) are listed in
                   <https://wiki.opennetworking.org/display/OTCC/Archived+Deliveries>";
        reference "ONF-TR-527, ONF-TR-512, ONF-TR-531, RFC 7950, RFC 6087 and ONF TAPI UML model
                  <https://github.com/OpenNetworkingFoundation/TAPI/tree/v2.3/UML>";
    }
    revision 2021-05-24 {
        description "ONF Transport API version 2.3 RC1.
                   Changes included in this TAPI release (v2.3) are listed in
                   <https://wiki.opennetworking.org/display/OTCC/Archived+Deliveries>";
        reference "ONF-TR-527, ONF-TR-512, ONF-TR-531, RFC 7950, RFC 6087 and ONF TAPI UML model
                  <https://github.com/OpenNetworkingFoundation/TAPI/tree/v2.3/UML>";
    }
    revision 2020-04-23 {
        description "ONF Transport API version 2.1.3.
                   Changes included in this TAPI release (v2.1.3) are listed in
                   <https://github.com/OpenNetworkingFoundation/TAPI/blob/develop_v2_1/CHANGE_LOG/change-log.2.1.3.md>";
        reference "ONF-TR-527, ONF-TR-512, ONF-TR-531, RFC 7950, RFC 6087 and ONF TAPI UML model
                  <https://github.com/OpenNetworkingFoundation/TAPI/tree/v2.1.3/UML>";
    }
    revision 2019-07-16 {
        description "ONF Transport API version 2.1.2.
                   Changes included in this TAPI release (v2.1.2) are listed in
                   <https://github.com/OpenNetworkingFoundation/TAPI/blob/develop_v2_1/CHANGE_LOG/change-log.2.1.2.md>";
        reference "ONF-TR-527, ONF-TR-512, ONF-TR-531, RFC 7950, RFC 6087 and ONF TAPI UML model
                  <https://github.com/OpenNetworkingFoundation/TAPI/tree/v2.1.2/UML>";
    }
    revision 2019-03-31 {
        description "ONF Transport API version 2.2-RC1.
                   Changes included in this TAPI release (v2.2) are listed in
                  <https://github.com/OpenNetworkingFoundation/TAPI/blob/develop/CHANGE_LOG/change-log.2.2.md>";
        reference "ONF-TR-527, ONF-TR-512, ONF-TR-531, RFC 7950, RFC 6087 and ONF TAPI UML model
                  <https://github.com/OpenNetworkingFoundation/TAPI/tree/v2.2.0/UML>";
    }
    revision 2018-12-10 {
        description "ONF Transport API version 2.1.1.
                   Changes included in this TAPI release (v2.1.1) are listed in
                  <https://github.com/OpenNetworkingFoundation/TAPI/blob/develop/CHANGE_LOG/change-log.2.1.1.md>";
        reference "ONF-TR-527, ONF-TR-512, ONF-TR-531, RFC 7950, RFC 6087 and ONF TAPI UML model
                  <https://github.com/OpenNetworkingFoundation/TAPI/tree/v2.1.1/UML>";
    }
    revision 2018-10-16 {
        description "ONF Transport API version 2.1.0.
                   Changes included in this TAPI release (v2.1.0) are listed in
                  <https://github.com/OpenNetworkingFoundation/TAPI/blob/develop/CHANGE_LOG/change-log.2.1.0.md>";
        reference "ONF-TR-527, ONF-TR-512, ONF-TR-531, RFC 7950, RFC 6087 and ONF TAPI UML model
                  <https://github.com/OpenNetworkingFoundation/TAPI/tree/v2.1.0/UML>";
    }
    revision 2018-03-07 {
        description "ONF Transport API version 2.0.2
        This YANG module has been generated from the TAPI UML Model using the IISOMI-Eagle xmi2yang mapping tool.
        Changes in this revision: <https://github.com/OpenNetworkingFoundation/TAPI/blob/develop/CHANGE_LOG/change-log.2.0.2.md>";
        reference "ONF-TR-527, ONF-TR-512, ONF-TR-531, RFC 6020, RFC 6087 and ONF TAPI UML model
                  <https://github.com/OpenNetworkingFoundation/TAPI/tree/v2.0.2/UML>";
    }
    revision 2018-02-16 {
        description "ONF Transport API version 2.0.1
        This YANG module has been generated from the TAPI UML Model using the IISOMI-Eagle xmi2yang mapping tool.
        Changes in this revision: <https://github.com/OpenNetworkingFoundation/TAPI/blob/develop/CHANGE_LOG/change-log.2.0.1.md>";
        reference "ONF-TR-527, ONF-TR-512, ONF-TR-531, RFC 6020, RFC 6087 and ONF TAPI UML model
                  <https://github.com/OpenNetworkingFoundation/TAPI/tree/v2.0.1/UML>";
    }
    revision 2018-01-02 {
        description "ONF Transport API version 2.0.0
        This YANG module has been generated from the TAPI UML Model using the IISOMI-Eagle xmi2yang mapping tool.
        Changes in this revision: <https://github.com/OpenNetworkingFoundation/TAPI/blob/develop/CHANGE_LOG/change-log.2.0.0.md>";
        reference "ONF-TR-527, ONF-TR-512, ONF-TR-531, RFC 6020, RFC 6087 and ONF TAPI UML model
                  <https://github.com/OpenNetworkingFoundation/TAPI/tree/v2.0.0/UML>";
    }
    augment "/tapi-common:context" {
        container virtual-network-context {
            uses virtual-network-context;
            description "Augments the base TAPI Context with VirtualNetworkContext model.";
        }
        description "Augments the base TAPI Context with VirtualNetworkContext model.";
    }
    augment "/tapi-streaming:stream-record/tapi-streaming:log-record/tapi-streaming:log-record-body" {
        when 'derived-from-or-self(tapi-streaming:record-content, "VIRTUAL_NETWORK_OBJECT_TYPE_VIRTUAL_NETWORK_SERVICE")';
        container virtual-network-service {
            uses virtual-network-service;
            description "none";
        }
        description "none";
    }
    augment "/tapi-streaming:stream-record/tapi-streaming:log-record/tapi-streaming:log-record-body" {
        when 'derived-from-or-self(tapi-streaming:record-content, "VIRTUAL_NETWORK_OBJECT_TYPE_VIRTUAL_NETWORK_SERVICE_END_POINT")';
        container virtual-network-service-end-point {
            uses virtual-network-service-end-point;
            description "none";
        }
        description "none";
    }
    augment "/tapi-streaming:stream-record/tapi-streaming:log-record/tapi-streaming:log-record-body" {
        when 'derived-from-or-self(tapi-streaming:record-content, "VIRTUAL_NETWORK_OBJECT_TYPE_VIRTUAL_NETWORK_CONSTRAINT")';
        container virtual-network-constraint {
            uses virtual-network-constraint;
            description "none";
        }
        description "none";
    }
    augment "/tapi-common:context/tapi-notification:notification-context/tapi-notification:event-notification" {
        when 'derived-from-or-self(tapi-notification:target-object-type, "VIRTUAL_NETWORK_OBJECT_TYPE_VIRTUAL_NETWORK_SERVICE_END_POINT")';
        container virtual-network-service-end-point {
            uses virtual-network-service-end-point;
            description "none";
        }
        description "none";
    }
    augment "/tapi-common:context/tapi-notification:notification-context/tapi-notification:event-notification" {
        when 'derived-from-or-self(tapi-notification:target-object-type, "VIRTUAL_NETWORK_OBJECT_TYPE_VIRTUAL_NETWORK_CONSTRAINT")';
        container virtual-network-constraint {
            uses virtual-network-constraint;
            description "none";
        }
        description "none";
    }
    augment "/tapi-notification:event-notification" {
        when 'derived-from-or-self(tapi-notification:target-object-type, "VIRTUAL_NETWORK_OBJECT_TYPE_VIRTUAL_NETWORK_SERVICE")';
        container virtual-network-service {
            uses virtual-network-service;
            description "none";
        }
        description "none";
    }
    augment "/tapi-notification:event-notification" {
        when 'derived-from-or-self(tapi-notification:target-object-type, "VIRTUAL_NETWORK_OBJECT_TYPE_VIRTUAL_NETWORK_SERVICE_END_POINT")';
        container virtual-network-service-end-point {
            uses virtual-network-service-end-point;
            description "none";
        }
        description "none";
    }
    augment "/tapi-notification:event-notification" {
        when 'derived-from-or-self(tapi-notification:target-object-type, "VIRTUAL_NETWORK_OBJECT_TYPE_VIRTUAL_NETWORK_CONSTRAINT")';
        container virtual-network-constraint {
            uses virtual-network-constraint;
            description "none";
        }
        description "none";
    }
    augment "/tapi-common:context/tapi-notification:notification-context/tapi-notification:event-notification" {
        when 'derived-from-or-self(tapi-notification:target-object-type, "VIRTUAL_NETWORK_OBJECT_TYPE_VIRTUAL_NETWORK_SERVICE")';
        container virtual-network-service {
            uses virtual-network-service;
            description "none";
        }
        description "none";
    }
    /**************************
    * definitions of references
    **************************/
    grouping virtual-nw-service-ref {
        leaf virtual-nw-service-uuid {
            type leafref {
                path '/tapi-common:context/tapi-virtual-network:virtual-network-context/tapi-virtual-network:virtual-nw-service/tapi-virtual-network:uuid';
            }
            description "none";
        }
        description "none";
    }
    
    /**************************
    * package object-classes
    **************************/ 
    grouping virtual-network-constraint {
        leaf-list service-layer {
            type tapi-common:layer-protocol-name;
            description "none";
        }
        leaf service-level {
            type string;
            description "An abstract value the meaning of which is mutually agreed – typically represents metrics such as - Class of service, priority, resiliency, availability";
        }
        container requested-capacity {
            uses tapi-common:capacity;
            description "none";
        }
        list cost-characteristic {
            key 'cost-name';
            uses tapi-topology:cost-characteristic;
            description "The list of costs where each cost relates to some aspect of the TopologicalEntity.";
        }
        list latency-characteristic {
            key 'traffic-property-name';
            uses tapi-topology:latency-characteristic;
            description "The effect on the latency of a queuing process. This only has significant effect for packet based systems and has a complex characteristic.";
        }
        container src-service-end-point {
            uses tapi-common:service-interface-point-ref;
            config false;
            description "none";
        }
        container sink-service-end-point {
            uses tapi-common:service-interface-point-ref;
            config false;
            description "none";
        }
        list diversity-exclusion {
            uses virtual-nw-service-ref;
            key 'virtual-nw-service-uuid';
            config false;
            description "none";
        }
        uses tapi-common:local-class;
        description "none";
    }
    grouping virtual-network-service {
        leaf-list layer-protocol-name {
            type tapi-common:layer-protocol-name;
            min-elements 1;
            description "none";
        }
        container topology {
            uses tapi-topology:topology-ref;
            config false;
            description "none";
        }
        list end-point {
            key 'local-id';
            min-elements 2;
            uses virtual-network-service-end-point;
            description "none";
        }
        list vnw-constraint {
            key 'local-id';
            min-elements 1;
            uses virtual-network-constraint;
            description "none";
        }
        container schedule {
            uses tapi-common:time-range;
            description "none";
        }
        container state {
            uses tapi-common:admin-state-pac;
            description "none";
        }
        uses tapi-common:global-class;
        description "The ForwardingConstruct (FC) object class models enabled potential for forwarding between two or more LTPs and like the LTP supports any transport protocol including all circuit and packet forms.
            At the lowest level of recursion, a FC represents a cross-connection within an NE.";
    }
    grouping virtual-network-service-end-point {
        leaf service-layer {
            type tapi-common:layer-protocol-name;
            config false;
            description "none";
        }
        leaf direction {
            type tapi-common:direction;
            config false;
            description "The direction of the end point.";
        }
        leaf role {
            type tapi-common:port-role;
            config false;
            description "The role of the (conceptual) port of the associated VirtualNetworkService.";
        }
        container service-interface-point {
            uses tapi-common:service-interface-point-ref;
            config false;
            description "none";
        }
        uses tapi-common:local-class;
        description "The association of the FC to LTPs is made via EndPoints.
            The EndPoint (EP) object class models the access to the FC function. 
            The traffic forwarding between the associated EPs of the FC depends upon the type of FC and may be associated with FcSwitch object instances.  
            In cases where there is resilience the EndPoint may convey the resilience role of the access to the FC. 
            It can represent a protected (resilient/reliable) point or a protecting (unreliable working or protection) point.
            The EP replaces the Protection Unit of a traditional protection model. 
            The ForwadingConstruct can be considered as a component and the EndPoint as a Port on that component";
    }
    grouping virtual-network-context {
        list virtual-nw-service {
            key 'uuid';
            uses virtual-network-service;
            description "none";
        }
        description "This object class represents the scope of control that a particular SDN controller has with respect to a particular network, specifically regarding the virtual network description.
            An instance of this class includes its VirtualNetworkService instances.";
    }

    /**************************
    * package type-definitions
    **************************/ 
    identity VIRTUAL_NETWORK_OBJECT_TYPE {
    	base tapi-common:OBJECT_TYPE;
        description "none";
    }
    identity VIRTUAL_NETWORK_OBJECT_TYPE_VIRTUAL_NETWORK_SERVICE {
        base VIRTUAL_NETWORK_OBJECT_TYPE;
        description "none";
    }
    identity VIRTUAL_NETWORK_OBJECT_TYPE_VIRTUAL_NETWORK_SERVICE_END_POINT {
        base VIRTUAL_NETWORK_OBJECT_TYPE;
        description "none";
    }
    identity VIRTUAL_NETWORK_OBJECT_TYPE_VIRTUAL_NETWORK_CONSTRAINT {
        base VIRTUAL_NETWORK_OBJECT_TYPE;
        description "The VirtualNetworkConstraint class.";
    }
    typedef virtual-network-object-type {
        type identityref {
            base VIRTUAL_NETWORK_OBJECT_TYPE;
        }
        description "The list of TAPI Virtual Network Object types/classes.";
    }

}
