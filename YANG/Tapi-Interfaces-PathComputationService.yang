module Tapi-Interfaces-PathComputationService {
    namespace "urn:ONF:Tapi-Interfaces-PathComputationService";
    prefix Tapi-Interfaces-PathComputationService;
    import Tapi-ObjectClasses {
        prefix Tapi-ObjectClasses;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-08 {
        description "Latest revision";
        reference "RFC 6020 and RFC 6087";
    }
    rpc computeP2PPath {
        description "none";
        input {
            list servicePort {
                min-elements 2;
                max-elements 2;
                uses Tapi-ObjectClasses:PathCompServicePort;
                description "none";
            }
            container routingConstraint {
                uses Tapi-ObjectClasses:ConnectivityConstraint;
                description "none";
            }
            container objectiveFunction {
                uses Tapi-ObjectClasses:PathObjectiveFunction;
                description "none";
            }
        }
        output {
            container pathCompService {
                uses Tapi-ObjectClasses:PathComputationService;
                description "none";
            }
        }
    }
    rpc optimizeP2PPath {
        description "none";
        input {
            leaf pathIdOrName {
                type string;
                description "none";
            }
            container routingConstraint {
                uses Tapi-ObjectClasses:ConnectivityConstraint;
                description "none";
            }
            container optimizationConstraint {
                uses Tapi-ObjectClasses:PathOptimizationConstraint;
                description "none";
            }
            container objectiveFunction {
                uses Tapi-ObjectClasses:PathObjectiveFunction;
                description "none";
            }
        }
        output {
            container pathCompService {
                uses Tapi-ObjectClasses:PathComputationService;
                description "none";
            }
        }
    }
    rpc deleteP2PPath {
        description "none";
        input {
            leaf pathIdOrName {
                type string;
                description "none";
            }
        }
        output {
            container pathCompService {
                uses Tapi-ObjectClasses:PathComputationService;
                description "none";
            }
        }
    }
}
