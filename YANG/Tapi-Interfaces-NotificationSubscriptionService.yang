module Tapi-Interfaces-NotificationSubscriptionService {
    namespace "urn:ONF:Tapi-Interfaces-NotificationSubscriptionService";
    prefix Tapi-Interfaces-NotificationSubscriptionService;
    import Tapi-TypeDefinitions {
        prefix Tapi-TypeDefinitions;
    }
    import Tapi-ObjectClasses {
        prefix Tapi-ObjectClasses;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-08 {
        description "Latest revision";
        reference "RFC 6020 and RFC 6087";
    }
    rpc getSupportedNotificationTypes {
        description "none";
        output {
            leaf-list supportedNotificationTypes {
                type Tapi-TypeDefinitions:NotificationType;
                min-elements 1;
                description "none";
            }
            leaf-list supportedObjectTypes {
                type Tapi-TypeDefinitions:ObjectType;
                min-elements 1;
                description "none";
            }
        }
    }
    rpc createNotificationSubscriptionService {
        description "none";
        input {
            container subscriptionFilter {
                uses Tapi-ObjectClasses:SubscriptionFilter;
                description "none";
            }
            leaf subscriptionState {
                type Tapi-TypeDefinitions:SubscriptionState;
                description "none";
            }
        }
        output {
            container subscriptionService {
                uses Tapi-ObjectClasses:NotificationSubscriptionService;
                description "none";
            }
        }
    }
    rpc updateNotificationSubscriptionService {
        description "none";
        input {
            leaf subscriptionIdOrName {
                type string;
                description "none";
            }
            container subscriptionFilter {
                uses Tapi-ObjectClasses:SubscriptionFilter;
                description "none";
            }
            leaf subscriptionState {
                type Tapi-TypeDefinitions:SubscriptionState;
                description "none";
            }
        }
        output {
            container subscriptionService {
                uses Tapi-ObjectClasses:NotificationSubscriptionService;
                description "none";
            }
        }
    }
    rpc deleteNotificationSubscriptionService {
        description "none";
        input {
            leaf subscriptionIdOrName {
                type string;
                description "none";
            }
        }
        output {
            container subscriptionService {
                uses Tapi-ObjectClasses:NotificationSubscriptionService;
                description "none";
            }
        }
    }
    rpc getNotificationSubscriptionServiceDetails {
        description "none";
        input {
            leaf subscriptionIdOrName {
                type string;
                description "none";
            }
        }
        output {
            container subscriptionService {
                uses Tapi-ObjectClasses:NotificationSubscriptionService;
                description "none";
            }
        }
    }
    rpc getNotificationSubscriptionServiceList {
        description "none";
        output {
            list subscriptionService {
                uses Tapi-ObjectClasses:NotificationSubscriptionService;
                description "none";
            }
        }
    }
    rpc getNotificationList {
        description "none";
        input {
            leaf subscriptionIdOrName {
                type string;
                description "none";
            }
            container timePeriod {
                uses Tapi-ObjectClasses:TimeRange;
                description "none";
            }
        }
        output {
            list notification {
                uses Tapi-ObjectClasses:Notification;
                description "none";
            }
        }
    }
}
