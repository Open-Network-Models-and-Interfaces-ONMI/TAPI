module TapiOduSpec-ObjectClasses {
    namespace "urn:ONF:TapiOduSpec-ObjectClasses";
    prefix TapiOduSpec-ObjectClasses;
    import TapiOduSpec-TypeDefinitions {
        prefix TapiOduSpec-TypeDefinitions;
    }
    import TapiSpec-ObjectClasses {
        prefix TapiSpec-ObjectClasses;
    }
    import Tapi-ObjectClasses {
        prefix Tapi-ObjectClasses;
    }    
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-08 {
        description "Latest revision";
        reference "RFC 6020 and RFC 6087";
    }
    grouping OduAdapterAndConnectionPointSpec {
        leaf adaptationActive {
            type boolean;
            config false;
            description "This attribute is applicable when the ODUk CTP object instance represents a lower order ODUk at the ODUkP/ODU[i]j or ODUkP/ODUj-21 adaptation function. This attribute indicates whether the adaptation function is activated or not. Valid values are true and false. The value of true means that the adaptation function shall access the access point when it is activated (MI_Active is true). Otherwise, it shall not access the access point.";
        }
        leaf apsEnable {
            type boolean;
            default "true";
            description "This attribute is for enabling/disabling the automatic protection switching (APS) capability at the transport adaptation function that is represented by the ODUk_ConnectionTerminationPoint object class. It triggers the MI_APS_EN signal to the transport adaptation function.";
        }
        leaf apsLevel {
            type uint64;
            description "This attribute is for configuring the automatic protection switching (APS) level that should operate at the transport adaptation function that is represented by the ODUk_ConnectionTerminationPoint object class. It triggers the MI_APS_LVL signal to the transport adaptation function. The value 0 means path and the values 1 through 6 mean TCM level 1 through 6 respectively.";
        }
        leaf k {
            type TapiOduSpec-TypeDefinitions:ODUk_CtpKBitRate;
            config false;
            description "This attribute specifies the index k that is used to represent a supported bit rate and the different versions of OPUk, ODUk and OTUk.
                When the ODU CTP is an instance of lower order ODU of a higher order ODU at the ODUkP/ODU[i]j adaptation function, valid values for the index and number of allowed instances of this object class are limited as specified in Table 14-27/G.798.  The restriction is basically HO index k=1, 2, 3 and LO j=0, 1, 2 with j less than k and optionally i=1 with i less than j.
                When the ODU CTP is an instance of lower order ODU of a higher order ODU at the client layer of the ODUkP/ODUj-21_A adaptation function, valid values for the index of this object class is limited by the rule HO index k=2, 3, 4 and LO j=0, 1, 2, 2e, 3, flex with j less than k.
                ";
        }
        leaf oduTypeAndRate {
            type uint64;
            description "This attribute is applicable when the ODUk CTP object instance represents a lower order ODUk CTP Source or Sink at the client layer of the ODUkP/ODUj-21 adaptation function. The value of this attribute specifies the type and rate of the adaptation and thus can be used to determine, according to Table 7-10/G.709, the mapping method and, in the case of GMP mapping, the base value and ranges for the parameters Cn and Cm. The value of this attribute is a triplet {j, k, size}, where j = 0, 1, 2, 2e, 3, flex; for the rate of the client ODUj  k = 1, 2, 3, 4; for the rate of the server ODUk size = 1.25G, 2.5G";
        }
        leaf-list positionSeq {
            type TapiOduSpec-TypeDefinitions:ODUk_TcmOrGccChoice;
            config false;
            description "This attribute indicates the positions of the TCM and GCC processing functions within the ODUk TP.
                The order of the position in the positionSeq attribute together with the signal flow determine the processing sequence of the TCM and GCC functions within the ODUk TP. Once the positions are determined, the signal processing sequence will follow the signal flow for each direction of the signal.
                Within the ODUk_CTP, the position order is going from adaptation to connection function. Within the ODUk_TTP, the order is going from connection to adaptation function.
                The syntax of the PositionSeq attribute will be a SEQUENCE OF pointers, which point to the contained TCM and GCC function.
                The order of TCM and GCC access function in the positionSeq attribute is significant only when there are more than one TCM functions within the ODUk TP and also at least one of them have the TimActDisabled attribute set to FALSE (i.e. AIS is inserted upon TIM).
                If a GCC12_TP is contained in an ODUk_TTP and the GCC12_TP is not listed in the PositionSeq attribute of the ODUk_TTP, then the GCC access is at the AP side of the ODUk TT function.
                ";
        }
        leaf-list tcmFieldsInUse {
            type uint64;
            config false;
            description "This attribute indicates the used TCM fields of the ODUk OH.";
        }
        leaf-list tributarySlotList {
            type uint64;
            config false;
            //min-elements 1;
            description "This attribute contains a set of distinct (i.e. unique) integers (e.g. 2, 3, 5, 9, 15 representing the tributary slots TS2, TS3, TS5, TS9 and TS15) which represents the resources occupied by the Low Order ODUk Link Connection (e.g. carrying an ODUflex with a bit rate of 6.25G). This attribute applies when the LO ODUk_ ConnectionTerminationPoint connects with an HO ODUk_TrailTerminationPoint object. It will not apply if this ODUk_ ConnectionTerminationPoint object directly connects to an OTUk_TrailTerminationPoint object (i.e. OTUk has no trib slots). The upper bound of the integer allowed in this set is a function of the HO-ODUk server layer to which the ODUk connection has been mapped (adapted). Thus, for example, M=8/32/80 for ODU2/ODU3/ODU4 server layers (respectively). Note that the value of this attribute can be changed only in the case of ODUflex and has to be through specific operations (i.e. not be changing the attribute tributarySlotList directly).";
        }
        leaf applicableProblems {
            type TapiOduSpec-TypeDefinitions:ODUk_CtpProblemList;
            config false;
            description "This attribute's datatype indicates the potential failure conditions of the entity.   The values are to be used in the inherited currentProblemList.";
        }
        leaf expectedMSI {
            type string;
            description "This attribute is applicable when the ODUk CTP object instance represents a lower order ODU1 or ODU2 CTP Sink at the client layer of the ODU3P/ODU12 adaptation function or represents a lower order ODUj CTP Sink at the client layer of the ODUkP/ODUj-21 adaptation function. This attribute is a 1-byte field that configures the expected multiplex structure of the adaptation function. ";
        }
        leaf acceptedMSI {
            type string;
            config false;
            description "This attribute is applicable when the ODUk CTP object instance represents a lower order ODU1 or ODU2 CTP Sink at the client layer of the ODU3P/ODU12 adaptation function or represents a lower order ODUj CTP Sink at the client layer of the ODUkP/ODUj-21 adaptation function. This attribute is a 1-byte field that represents the accepted multiplex structure of the adaptation function. ";
        }
        leaf acceptedPayloadType {
            type string;
            config false;
            description "This attribute is applicable when the ODUk CTP object instance represents a lower order ODUk CTP Sink at the client layer of the ODUkP/ODU[i]j or ODUkP/ODUj-21 adaptation function. This attribute is a 2-digit Hex code that indicates the new accepted payload type. ";
        }
        leaf transmittedMSI {
            type string;
            description "This attribute is applicable when the ODUk CTP object instance represents a lower order ODU1 or ODU2 CTP Source at the client layer of the ODU3P/ODU12 adaptation function, or a lower order ODUj CTP Source at the client layer of the ODUkP/ODUj-21 adaptation function. This attribute is a 1-byte field that configures the transmitted multiplex structure identifier of the adaptation function.";
        }
        leaf autoPayloadType {
            type boolean;
            description "This attribute is applicable when the ODUk CTP object instance represents a lower order ODU CTP Source at the client layer of the ODUkP/ODUj-21 adaptation function. The value of true of this attribute configures that the adaptation source function shall fall back to the payload type PT=20 if the conditions specified in 14.3.10.1/G.798 are satisfied. ";
        }
        leaf insertedPayloadType {
            type string;
            config false;
            description "This attribute is applicable when the ODUk CTP object instance represents a lower order ODU CTP Source at the client layer of the ODUkP/ODUj-21 adaptation function. The attribute reports the inserted payload type (i.e. TrPT) for the PT byte position of the PSI overhead. Valid values for this attribute are 20 and 21. For more details see 14.3.10.1/G.798. ";
        }
        list tandem {
            key 'tcmField';
            max-elements 12;
            uses OduTCMSpec;
            description "none";
        }
        leaf-list currentNumberOfTributarySlots {
            type uint64;
            config false;
            //min-elements 1;
            description "This attribute applies only to ODUflex(GFP) connections. It represents the current number of tributary slots allocated to this ODUflex(GFP) connection in the HO-ODU server layer. The value of this parameter determines the bit rate of the ODUflex connection. 
                The upper bound of this attribute is dependent on the HO-ODUk server layer. 
                When the ODUflex(GFP) connection is initially created, this represents the actual number of tributary slots in use for the connection. When an ODUflex(GFP) connection is undergoing a resize operation, this attribute reflects the desired (resized) number of tributary slots only after the following stages (see G.7044[5] for details):
                - After the Bandwidth Resize (BWR) phase completes (In the case of bandwidth increase)
                - After the Link Connection Resize (LCR) phase of the ODUflex resize operation (in the case of bandwidth decrease)
                This attribute applies only to ODUflex(CBR) connections only. The value of this attribute is (239/238)* (Bit rate of the CBR client).
                ";
        }
        leaf resizingProtocolStatus {
            type TapiOduSpec-TypeDefinitions:ODUk_h_ResizingProtocolStatus;
            config false;
            description "This attribute indicates the status of the resizing protocol.";
        }
        container nominalBitRateAndTolerance {
            uses TapiOduSpec-TypeDefinitions:ODUk_h_nominalBitRateAndTolerance;
            description "This attribute specifies the nominal clock frequency and its tolerance range. Valid values for the frequency (in kHz) and tolerance (in ppm) range are given in Table 14-2/G.798 and clause 12.2.5/G.709.";
        }
        description "none";
    }
    grouping OduTerminationSpec {
        leaf k {
            type TapiOduSpec-TypeDefinitions:ODUk_TtpKBitRate;
            config false;
            description "This attribute specifies the index k that is used to represent a supported bit rate and the different versions of OPUk, ODUk and OTUk.";
        }
        leaf-list positionSeq {
            type TapiOduSpec-TypeDefinitions:ODUk_TcmOrGccChoice;
            config false;
            description "This attribute indicates the positions of the TCM and GCC processing functions within the ODUk TP.
                The order of the position in the positionSeq attribute together with the signal flow determine the processing sequence of the TCM and GCC functions within the ODUk TP. Once the positions are determined, the signal processing sequence will follow the signal flow for each direction of the signal.
                Within the ODUk_CTP, the position order is going from adaptation to connection function. Within the ODUk_TTP, the order is going from connection to adaptation function.
                The syntax of the PositionSeq attribute will be a SEQUENCE OF pointers, which point to the contained TCM and GCC function.
                The order of TCM and GCC access function in the positionSeq attribute is significant only when there are more than one TCM functions within the ODUk TP and also at least one of them have the TimActDisabled attribute set to FALSE (i.e. AIS is inserted upon TIM).
                If a GCC12_TP is contained in an ODUk_TTP and the GCC12_TP is not listed in the PositionSeq attribute of the ODUk_TTP, then the GCC access is at the AP side of the ODUk TT function.
                ";
        }
        leaf rate {
            type string;
            config false;
            description "This attribute applies only to ODUflex(CBR) connections only. The value of this attribute is (239/238)* (Bit rate of the CBR client).
                ";
        }
        leaf dmSource {
            type boolean;
            description "This attribute is for configuring the delay measurement process at the trail termination function represented by the subject TTP object class. It models the MI_DM_Source MI signal. If MI_DM_Source is false, then the value of the DMp bit is determined by the RI_DM. If MI_DM_Source is true, then the value of the DMp bit is set to MI_DMValue.";
        }
        leaf dmValue {
            type boolean;
            description "This attribute is for setting the DMp and DMti bits of the delay measurement process. The value of true sets the DMp and DMti bits to 0 and the value of false to 1.";
        }
        leaf-list tcmFieldsInUse {
            type uint64;
            config false;
            description "This attribute indicates the used TCM fields of the ODUk OH.";
        }
        leaf acti {
            type TapiOduSpec-TypeDefinitions:BitString;
            config false;
            description "The Trail Trace Identifier (TTI) information recovered (Accepted) from the TTI overhead position at the sink of a trail.";
        }
        leaf degM {
            type uint64;
            description "This attribute indicates the threshold level for declaring a Degraded Signal defect (dDEG). A dDEG shall be declared if DegM consecutive bad PM Seconds are detected.";
        }
        container degThr {
            uses TapiOduSpec-TypeDefinitions:DegThr;
            description "This attribute indicates the threshold level for declaring a performance monitoring (PM) Second to be bad. The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.";
        }
        leaf exDapi {
            type TapiOduSpec-TypeDefinitions:BitString;
            description "The Expected Destination Access Point Identifier (ExDAPI), provisioned by the managing system, to be compared with the TTI accepted at the overhead position of the sink for the purpose of checking the integrity of connectivity.";
        }
        leaf exSapi {
            type TapiOduSpec-TypeDefinitions:BitString;
            description "The Expected Source Access Point Identifier (ExSAPI), provisioned by the managing system, to be compared with the TTI accepted at the overhead position of the sink for the purpose of checking the integrity of connectivity.";
        }
        leaf timActDisabled {
            type boolean;
            description "This attribute provides the control capability for the managing system to enable or disable the Consequent Action function when detecting Trace Identifier Mismatch (TIM) at the trail termination sink. The value of TRUE means disabled.";
        }
        leaf timDetMode {
            type TapiOduSpec-TypeDefinitions:TimDetMo;
            description "This attribute indicates the mode of the Trace Identifier Mismatch (TIM) Detection functionallowed values: off, SAPIonly, DAPIonly, SAPIandDAPI";
        }
        leaf txti {
            type TapiOduSpec-TypeDefinitions:BitString;
            description "The Trail Trace Identifier (TTI) information, provisioned by the managing system at the termination source, to be placed in the TTI overhead position of the source of a trail for transmission.";
        }
        leaf-list currentNumberOfTributarySlots {
            type uint64;
            config false;
            //min-elements 1;
            description "This attribute applies only to ODUflex(GFP) connections. It represents the current number of tributary slots allocated to this ODUflex(GFP) connection in the HO-ODU server layer. The value of this parameter determines the bit rate of the ODUflex connection. 
                The upper bound of this attribute is dependent on the HO-ODUk server layer. 
                When the ODUflex(GFP) connection is initially created, this represents the actual number of tributary slots in use for the connection. When an ODUflex(GFP) connection is undergoing a resize operation, this attribute reflects the desired (resized) number of tributary slots only after the following stages (see G.7044[5] for details):
                - After the Bandwidth Resize (BWR) phase completes (In the case of bandwidth increase)
                - After the Link Connection Resize (LCR) phase of the ODUflex resize operation (in the case of bandwidth decrease)
                This attribute applies only to ODUflex(CBR) connections only. The value of this attribute is (239/238)* (Bit rate of the CBR client).
                ";
        }
        leaf resizingProtocolStatus {
            type TapiOduSpec-TypeDefinitions:ODUk_h_ResizingProtocolStatus;
            config false;
            description "This attribute indicates the status of the resizing protocol.";
        }
        description "none";
    }
    grouping OduLpSpec {
        //key 'lpSpecReference';
        container _adapterSpec {
            uses OduAdapterAndConnectionPointSpec;
            description "none";
        }
        container _terminationSpec {
            uses OduTerminationSpec;
            description "none";
        }
        //uses TapiSpec-ObjectClasses:LpSpec;
        description "none";
    }
    augment "/Tapi-ObjectClasses:Context/Tapi-ObjectClasses:_serviceEndPoint/Tapi-ObjectClasses:_layerProtocol/Tapi-ObjectClasses:_lpSpecData" {
        uses OduLpSpec;
    }
    
    augment "/Tapi-ObjectClasses:Context/Tapi-ObjectClasses:_serviceEndPoint/Tapi-ObjectClasses:_connectionEndPoint/Tapi-ObjectClasses:_layerProtocol/Tapi-ObjectClasses:_lpSpecData" {
        uses OduLpSpec;
    }
    
    augment "/Tapi-ObjectClasses:Context/Tapi-ObjectClasses:_topology/Tapi-ObjectClasses:_node/Tapi-ObjectClasses:_ownedNodeEdgePoint/Tapi-ObjectClasses:_layerProtocol/Tapi-ObjectClasses:_lpSpecData" {
        uses OduLpSpec;
    }    
    grouping OduTCMSpec {
        leaf tcmField {
            type uint64;
            description "This attribute indicates the tandem connection monitoring field of the ODUk OH.";
        }
        leaf mode {
            type TapiOduSpec-TypeDefinitions:TcmMode;
            description "This attribute specifies the TCM mode at the entity. Valid values are: Operational, Monitor, and Transparent.";
        }
        leaf codirectional {
            type boolean;
            config false;
            description "This attribute specifies the directionality of the ODUkT TP with respect to the associated ODUk CTP. The value of TRUE means that the sink part of the ODUkT TP terminates the same signal direction as the sink part of the ODUk CTP. The Source part behaves similarly. This attribute is meaningful only on objects instantiated under ODUk CTP, and at least one among ODUk CTP and the subordinate object is bidirectional.";
        }
        leaf tcmExtension {
            type TapiOduSpec-TypeDefinitions:ODUkT_tcmExtension;
            description "none";
        }
        leaf dmSource {
            type boolean;
            description "This attribute is for configuring the delay measurement process at the trail termination function represented by the subject TTP object class. It models the MI_DM_Source MI signal. If MI_DM_Source is false, then the value of the DMp bit is determined by the RI_DM. If MI_DM_Source is true, then the value of the DMp bit is set to MI_DMValue.";
        }
        leaf dmValue {
            type boolean;
            description "This attribute is for setting the DMp and DMti bits of the delay measurement process. The value of “true” sets the DMp and DMti bits to 0 and the value of “false” to 1.";
        }
        leaf acStatusSink {
            type TapiOduSpec-TypeDefinitions:ODUk_TcmStatus;
            config false;
            description "This attribute indicates the status of the accepted TCM. ";
        }
        leaf acti {
            type TapiOduSpec-TypeDefinitions:BitString;
            config false;
            description "The Trail Trace Identifier (TTI) information recovered (Accepted) from the TTI overhead position at the sink of a trail.";
        }
        leaf adminStateSink {
            type TapiOduSpec-TypeDefinitions:ODUkT_AdministrationState;
            description "This attribute provides the capability to provision the LOCK signal at the sink, which is one of the ODUk maintenance signals. When a Tandem Connection endpoint is set to admin state locked, it will insert the ODUk-LCK signal in the downstream direction.";
        }
        leaf degM {
            type uint64;
            description "This attribute indicates the threshold level for declaring a Degraded Signal defect (dDEG). A dDEG shall be declared if DegM consecutive bad PM Seconds are detected.";
        }
        container degThr {
            uses TapiOduSpec-TypeDefinitions:DegThr;
            description "This attribute indicates the threshold level for declaring a performance monitoring (PM) Second to be bad. The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.";
        }
        leaf exDapi {
            type TapiOduSpec-TypeDefinitions:BitString;
            description "The Expected Destination Access Point Identifier (ExDAPI), provisioned by the managing system, to be compared with the TTI accepted at the overhead position of the sink for the purpose of checking the integrity of connectivity.";
        }
        leaf exSapi {
            type TapiOduSpec-TypeDefinitions:BitString;
            description "The Expected Source Access Point Identifier (ExSAPI), provisioned by the managing system, to be compared with the TTI accepted at the overhead position of the sink for the purpose of checking the integrity of connectivity.";
        }
        leaf timActDisabled {
            type boolean;
            description "This attribute provides the control capability for the managing system to enable or disable the Consequent Action function when detecting Trace Identifier Mismatch (TIM) at the trail termination sink. The value of TRUE means disabled.";
        }
        leaf timDetMode {
            type TapiOduSpec-TypeDefinitions:TimDetMo;
            description "This attribute indicates the mode of the Trace Identifier Mismatch (TIM) Detection functionallowed values: off, SAPIonly, DAPIonly, SAPIandDAPI";
        }
        leaf acStatusSource {
            type TapiOduSpec-TypeDefinitions:ODUk_TcmStatus;
            config false;
            description "This attribute indicates the status of the accepted TCM. ";
        }
        leaf adminStateSource {
            type TapiOduSpec-TypeDefinitions:ODUkT_AdministrationState;
            description "This attribute provides the capability to provision the LOCK signal at the source, which is one of the ODUk maintenance signals.  When a Tandem Connection endpoint is set to admin state locked, it will insert the ODUk-LCK signal in the source direction.";
        }
        leaf txti {
            type TapiOduSpec-TypeDefinitions:BitString;
            description "The Trail Trace Identifier (TTI) information, provisioned by the managing system at the termination source, to be placed in the TTI overhead position of the source of a trail for transmission.";
        }
        description "none";
    }
}
