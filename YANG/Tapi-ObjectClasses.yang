module Tapi-ObjectClasses {
    namespace "urn:ONF:Tapi-ObjectClasses";
    prefix Tapi-ObjectClasses;
    import Tapi-TypeDefinitions {
        prefix Tapi-TypeDefinitions;
    }
    import TapiSpec-ObjectClasses {
        prefix TapiSpec-ObjectClasses;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-08 {
        description "Latest revision";
        reference "RFC 6020 and RFC 6087";
    }
    container Context {
        list _connectivityService {
            key 'uuid';
            uses ConnectivityService;
            description "none";
        }
        list _vnwService {
            key 'uuid';
            uses VirtualNetworkService;
            description "none";
        }
        list _pathCompService {
            key 'uuid';
            uses PathComputationService;
            description "none";
        }
        list _notifSubscription {
            key 'uuid';
            uses NotificationSubscriptionService;
            description "none";
        }
        list _serviceEndPoint {
            key 'uuid';
            min-elements 2;
            config false;
            uses ServiceEndPoint;
            description "none";
        }
        list _topology {
            key 'uuid';
            config false;
            uses Topology;
            description "none";
        }
        list _notification {
            key 'notificationId';
            config false;
            uses Notification;
            description "none";
        }
        uses GlobalClass;
        description "The Network Control Domain (NCD) object class represents the scope of control that a particular SDN controller has with respect to a particular network, (i.e., encompassing a designated set of interconnected (virtual) network elements).";
    }
    grouping Topology {
        list _node {
            key 'uuid';
            config false;
            uses Node;
            description "none";
        }
        list _link {
            key 'uuid';
            config false;
            uses Link;
            description "none";
        }
        leaf-list layerProtocolName {
            type Tapi-TypeDefinitions:LayerProtocolName;
            config false;
            min-elements 1;
            description "none";
        }
        uses GlobalClass;
        description "The ForwardingDomain (FD) object class models the “ForwardingDomain” topological component which is used to effect forwarding of transport characteristic information and offers the potential to enable forwarding. 
            At the lowest level of recursion, an FD (within a network element (NE)) represents a switch matrix (i.e., a fabric). Note that an NE can encompass multiple switch matrices (FDs). ";
    }
    grouping Node {
        list _ownedNodeEdgePoint {
            key 'uuid';
            config false;
            uses NodeEdgePoint;
            description "none";
        }
        leaf-list _aggregatedNodeEdgePoint {
            type leafref {
                path '/Context/_topology/_node/_ownedNodeEdgePoint/uuid';
            }
            config false;
            description "none";
        }
        leaf _encapTopology {
            type leafref {
                path '/Context/_topology/uuid';
            }
            config false;
            description "none";
        }
        container _state {
            config false;
            uses AdminStatePac;
            description "none";
        }
        container _transferCapacity {
            config false;
            uses TransferCapacityPac;
            description "none";
        }
        container _transferCost {
            config false;
            uses TransferCostPac;
            description "none";
        }
        container _transferIntegrity {
            config false;
            uses TransferIntegrityPac;
            description "none";
        }
        container _transferTiming {
            config false;
            uses TransferTimingPac;
            description "none";
        }
        leaf-list layerProtocolName {
            type Tapi-TypeDefinitions:LayerProtocolName;
            config false;
            min-elements 1;
            description "none";
        }
        uses GlobalClass;
        description "The ForwardingDomain (FD) object class models the “ForwardingDomain” topological component which is used to effect forwarding of transport characteristic information and offers the potential to enable forwarding. 
            At the lowest level of recursion, an FD (within a network element (NE)) represents a switch matrix (i.e., a fabric). Note that an NE can encompass multiple switch matrices (FDs). ";
    }
    grouping Link {
        list _linkPort {
            key 'localId';
            min-elements 2;
            config false;
            uses LinkPort;
            description "none";
        }
        leaf-list _node {
            type leafref {
                path '/Context/_topology/_node/uuid';
            }
            config false;
            min-elements 2;
            description "none";
        }
        container _state {
            config false;
            uses AdminStatePac;
            description "none";
        }
        container _transferCapacity {
            config false;
            uses TransferCapacityPac;
            description "none";
        }
        container _transferCost {
            config false;
            uses TransferCostPac;
            description "none";
        }
        container _transferIntegrity {
            config false;
            uses TransferIntegrityPac;
            description "none";
        }
        container _transferTiming {
            config false;
            uses TransferTimingPac;
            description "none";
        }
        container _riskParameter {
            config false;
            uses RiskParameterPac;
            description "none";
        }
        container _validation {
            config false;
            uses ValidationPac;
            description "none";
        }
        container _lpTransition {
            config false;
            uses LayerProtocolTransitionPac;
            description "none";
        }
        leaf-list layerProtocolName {
            type Tapi-TypeDefinitions:LayerProtocolName;
            config false;
            min-elements 1;
            description "none";
        }
        leaf direction {
            type Tapi-TypeDefinitions:ForwardingDirection;
            config false;
            description "The directionality of the Link. 
                Is applicable to simple Links where all LinkEnds are BIDIRECTIONAL (the Link will be BIDIRECTIONAL) or UNIDIRECTIONAL (the Link will be UNIDIRECTIONAL). 
                Is not present in more complex cases.";
        }
        uses GlobalClass;
        description "The Link object class models effective adjacency between two or more ForwardingDomains (FD). ";
    }
    grouping NodeEdgePoint {
        container _ltpSpecData {
            config false;
            uses TapiSpec-ObjectClasses:LtpSpec;
            description "none";
        }
        list _layerProtocol {
            key 'localId';
            min-elements 1;
            config false;
            uses LayerProtocol;
            description "none";
        }
        leaf-list _clientNodeEdgePoint {
            type leafref {
                path '/Context/_topology/_node/_ownedNodeEdgePoint/uuid';
            }
            config false;
            description "none";
        }
        container _state {
            config false;
            uses AdminStatePac;
            description "none";
        }
        leaf direction {
            type Tapi-TypeDefinitions:TerminationDirection;
            config false;
            description "none";
        }
        uses GlobalClass;
        description "The LogicalTerminationPoint (LTP) object class encapsulates the termination and adaptation functions of one or more transport layers. 
            The structure of LTP supports all transport protocols including circuit and packet forms.";
    }
    grouping ServiceEndPoint {
        container _ltpSpecData {
            config false;
            uses TapiSpec-ObjectClasses:LtpSpec;
            description "none";
        }
        list _layerProtocol {
            key 'localId';
            min-elements 1;
            config false;
            uses LayerProtocol;
            description "none";
        }
        leaf-list _mappedNodeEdgePoint {
            type leafref {
                path '/Context/_topology/_node/_ownedNodeEdgePoint/uuid';
            }
            config false;
            description "none";
        }
        list _connectionEndPoint {
            key 'uuid';
            config false;
            uses ConnectionEndPoint;
            description "none";
        }
        container _state {
            config false;
            uses LifecycleStatePac;
            description "none";
        }
        leaf direction {
            type Tapi-TypeDefinitions:TerminationDirection;
            config false;
            description "none";
        }
        uses GlobalClass;
        description "The LogicalTerminationPoint (LTP) object class encapsulates the termination and adaptation functions of one or more transport layers. 
            The structure of LTP supports all transport protocols including circuit and packet forms.";
    }
    grouping ConnectionEndPoint {
        container _ltpSpecData {
            config false;
            uses TapiSpec-ObjectClasses:LtpSpec;
            description "none";
        }
        list _layerProtocol {
            key 'localId';
            min-elements 1;
            config false;
            uses LayerProtocol;
            description "none";
        }
        leaf-list _clientNodeEdgePoint {
            type leafref {
                path '/Context/_topology/_node/_ownedNodeEdgePoint/uuid';
            }
            config false;
            description "none";
        }
        leaf _serverNodeEdgePoint {
            type leafref {
                path '/Context/_topology/_node/_ownedNodeEdgePoint/uuid';
            }
            config false;
            description "none";
        }
        leaf _peerConnectionEndPoint {
            type leafref {
                path '/Context/_serviceEndPoint/_connectionEndPoint/uuid';
            }
            config false;
            description "none";
        }
        container _state {
            config false;
            uses OperationalStatePac;
            description "none";
        }
        leaf direction {
            type Tapi-TypeDefinitions:TerminationDirection;
            config false;
            description "none";
        }
        uses GlobalClass;
        description "The LogicalTerminationPoint (LTP) object class encapsulates the termination and adaptation functions of one or more transport layers. 
            The structure of LTP supports all transport protocols including circuit and packet forms.";
    }
    grouping ConnectivityService {
        list _connection {
            key 'uuid';
            config false;
            uses Connection;
            description "none";
        }
        list _servicePort {
            key 'localId';
            min-elements 2;
            uses ConnectivityServicePort;
            description "none";
        }
        container _connConstraints {
            uses ConnectivityConstraint;
            description "none";
        }
        container _schedule {
            uses TimeRange;
            description "none";
        }
        container _state {
            uses AdminStatePac;
            description "none";
        }
        leaf layerProtocolName {
            type Tapi-TypeDefinitions:LayerProtocolName;
            description "none";
        }
        leaf direction {
            type Tapi-TypeDefinitions:ForwardingDirection;
            description "none";
        }
        uses GlobalClass;
        description "The ForwardingConstruct (FC) object class models enabled potential for forwarding between two or more LTPs and like the LTP supports any transport protocol including all circuit and packet forms.
            At the lowest level of recursion, a FC represents a cross-connection within an NE.";
    }
    grouping Connection {
        list _connectionPort {
            key 'localId';
            min-elements 2;
            config false;
            uses ConnectionPort;
            description "none";
        }
        list _route {
            key 'localId';
            config false;
            uses Route;
            description "none";
        }
        leaf _node {
            type leafref {
                path '/Context/_topology/_node/uuid';
            }
            config false;
            description "none";
        }
        container _state {
            config false;
            uses OperationalStatePac;
            description "none";
        }
        leaf layerProtocolName {
            type Tapi-TypeDefinitions:LayerProtocolName;
            config false;
            description "none";
        }
        leaf direction {
            type Tapi-TypeDefinitions:ForwardingDirection;
            config false;
            description "none";
        }
        uses GlobalClass;
        description "The ForwardingConstruct (FC) object class models enabled potential for forwarding between two or more LTPs and like the LTP supports any transport protocol including all circuit and packet forms.
            At the lowest level of recursion, a FC represents a cross-connection within an NE.";
    }
    grouping Route {
        leaf-list _lowerConnection {
            type leafref {
                path '/Context/_connectivityService/_connection/uuid';
            }
            config false;
            min-elements 1;
            description "none";
        }
        uses LocalClass;
        description "The FC Route (FcRoute) object class models the individual routes of an FC. 
            The route of an FC object is represented by a list of FCs at a lower level. 
            Note that depending on the service supported by an FC, an the FC can have multiple routes.";
    }
    grouping LinkPort {
        leaf _nodeEdgePoint {
            type leafref {
                path '/Context/_topology/_node/_ownedNodeEdgePoint/uuid';
            }
            config false;
            description "none";
        }
        leaf role {
            type Tapi-TypeDefinitions:PortRole;
            config false;
            description "Each LinkEnd of the Link has a role (e.g., symmetric, hub, spoke, leaf, root)  in the context of the Link with respect to the Link function. ";
        }
        leaf direction {
            type Tapi-TypeDefinitions:PortDirection;
            config false;
            description "The orientation of defined flow at the LinkEnd.";
        }
        uses LocalClass;
        description "The association of the Link to LTPs is made via LinkEnd.
            The LinkEnd object class models the access to the Link function. 
            The traffic forwarding between the associated LinkEnds of the Link depends upon the type of Link.  
            In cases where there is resilience the LinkEnd may convey the resilience role of the access to the Link. 
            The Link can be considered as a component and the LinkEnd as a Port on that component";
    }
    grouping ConnectivityServicePort {
        leaf _serviceEndPoint {
            type leafref {
                path '/Context/_serviceEndPoint/uuid';
            }
            config false;
            description "none";
        }
        leaf role {
            type Tapi-TypeDefinitions:PortRole;
            config false;
            description "Each EP of the FC has a role (e.g., working, protection, protected, symmetric, hub, spoke, leaf, root)  in the context of the FC with respect to the FC function. ";
        }
        leaf direction {
            type Tapi-TypeDefinitions:PortDirection;
            config false;
            description "The orientation of defined flow at the EndPoint.";
        }
        leaf serviceLayer {
            type Tapi-TypeDefinitions:LayerProtocolName;
            config false;
            description "none";
        }
        uses LocalClass;
        description "The association of the FC to LTPs is made via EndPoints.
            The EndPoint (EP) object class models the access to the FC function. 
            The traffic forwarding between the associated EPs of the FC depends upon the type of FC and may be associated with FcSwitch object instances.  
            In cases where there is resilience the EndPoint may convey the resilience role of the access to the FC. 
            It can represent a protected (resilient/reliable) point or a protecting (unreliable working or protection) point.
            The EP replaces the Protection Unit of a traditional protection model. 
            The ForwadingConstruct can be considered as a component and the EndPoint as a Port on that component";
    }
    grouping ConnectionPort {
        leaf _connectionEndPoint {
            type leafref {
                path '/Context/_serviceEndPoint/_connectionEndPoint/uuid';
            }
            config false;
            description "none";
        }
        leaf role {
            type Tapi-TypeDefinitions:PortRole;
            config false;
            description "Each EP of the FC has a role (e.g., working, protection, protected, symmetric, hub, spoke, leaf, root)  in the context of the FC with respect to the FC function. ";
        }
        leaf direction {
            type Tapi-TypeDefinitions:PortDirection;
            config false;
            description "The orientation of defined flow at the EndPoint.";
        }
        uses LocalClass;
        description "The association of the FC to LTPs is made via EndPoints.
            The EndPoint (EP) object class models the access to the FC function. 
            The traffic forwarding between the associated EPs of the FC depends upon the type of FC and may be associated with FcSwitch object instances.  
            In cases where there is resilience the EndPoint may convey the resilience role of the access to the FC. 
            It can represent a protected (resilient/reliable) point or a protecting (unreliable working or protection) point.
            The EP replaces the Protection Unit of a traditional protection model. 
            The ForwadingConstruct can be considered as a component and the EndPoint as a Port on that component";
    }
    grouping LayerProtocol {
        container _lpSpecData {
            config false;
            uses TapiSpec-ObjectClasses:LpSpec;
            description "none";
        }
        leaf layerProtocolName {
            type Tapi-TypeDefinitions:LayerProtocolName;
            description "Indicate the specific layer-protocol described by the LayerProtocol entity.";
        }
        leaf terminationDirection {
            type Tapi-TypeDefinitions:TerminationDirection;
            description "The overall directionality of the LP. 
                - A BIDIRECTIONAL LP will have some SINK and/or SOURCE flowss.
                - A SINK LP can only contain elements with SINK flows or CONTRA_DIRECTION_SOURCE flows
                - A SOURCE LP can only contain SOURCE flows or CONTRA_DIRECTION_SINK flows";
        }
        leaf terminationState {
            type Tapi-TypeDefinitions:TerminationState;
            description "Indicates whether the layer is terminated and if so how.";
        }
        uses LocalClass;
        description "Each transport layer is represented by a LayerProtocol (LP) instance. The LayerProtocol instances it can be used for controlling termination and monitoring functionality. 
            It can also be used for controlling the adaptation (i.e. encapsulation and/or multiplexing of client signal), tandem connection monitoring, traffic conditioning and/or shaping functionality at an intermediate point along a connection. 
            Where the client – server relationship is fixed 1:1 and immutable, the layers can be encapsulated in a single LTP instance. Where the is a n:1 relationship between client and server, the layers must be split over two separate instances of LTP. ";
    }
    grouping TransferCostPac {
        list costCharacteristic {
            key 'costAlgorithm';
            min-elements 1;
            config false;
            uses Tapi-TypeDefinitions:CostCharacteristic;
            description "The list of costs where each cost relates to some aspect of the TopologicalEntity.";
        }
        description "The cost characteristics of a TopologicalEntity not necessarily correlated to the cost of the underlying physical realization. 
            They may be quite specific to the individual TopologicalEntity e.g. opportunity cost. Relates to layer capacity
            There may be many perspectives from which cost may be considered  for a particular TopologicalEntity and hence many specific costs and potentially cost algorithms. 
            Using an entity will incur a cost. ";
    }
    grouping RiskParameterPac {
        list riskCharacteristic {
            key 'riskCharacteristicName';
            min-elements 1;
            config false;
            uses Tapi-TypeDefinitions:RiskCharacteristic;
            description "A list of risk characteristics for consideration in an analysis of shared risk. Each element of the list represents a specific risk consideration.";
        }
        description "The risk characteristics of a TopologicalEntity come directly from the underlying physical realization. 
            The risk characteristics propagate from the physical realization to the client and from the server layer to the client layer, this propagation may be modified by protection.
            A TopologicalEntity may suffer degradation or failure as a result of a problem in a part of the underlying realization.
            The realization can be partitioned into segments which have some relevant common failure modes.
            There is a risk of failure/degradation of each segment of the underlying realization.
            Each segment is a part of a larger physical/geographical unit that behaves as one with respect to failure (i.e. a failure will have a high probability of impacting the whole unit (e.g. all cables in the same duct).
            Disruptions to that larger physical/geographical unit will impact (cause failure/errors to) all TopologicalEntities that use any part of that larger physical/geographical entity.
            Any TopologicalEntity that uses any part of that larger physical/geographical unit will suffer impact and hence each TopologicalEntity shares risk.
            The identifier of each physical/geographical unit that is involved in the realization of each segment of a Topological entity can be listed in the RiskParameter_Pac of that TopologicalEntity.
            A segment has one or more risk characteristic.
            Shared risk between two TopologicalEntities compromises the integrity of any solution that use one of those TopologicalEntity as a backup for the other.
            Where two TopologicalEntities have a common risk characteristic they have an elevated probability of failing simultaneously compared to two TopologicalEntities that do not share risk characteristics.";
    }
    grouping LayerProtocolTransitionPac {
        leaf-list transitionedLayerProtocolName {
            type string;
            min-elements 1;
            description "Provides the ordered structure of layer protocol transitions encapsulated in the TopologicalEntity. The ordering relates to the LinkPort role.";
        }
        leaf-list _nodeEdgePoint {
            type leafref {
                path '/Context/_topology/_node/_ownedNodeEdgePoint/uuid';
            }
            min-elements 1;
            description "Lists the LTPs that define the layer protocol transition of the transitional link.";
        }
        description "Relevant for a Link that is formed by abstracting one or more LTPs (in a stack) to focus on the flow and deemphasize the protocol transformation. 
            This abstraction is relevant when considering multi-layer routing. 
            The layer protocols of the LTP and the order of their application to the signal is still relevant and need to be accounted for. This is derived from the LTP spec details.
            This Pac provides the relevant abstractions of the LTPs and provides the necessary association to the LTPs involved.
            Links that included details in this Pac are often referred to as Transitional Links.";
    }
    grouping TransferTimingPac {
        leaf fixedLatencyCharacteristic {
            type string;
            config false;
            description "A TopologicalEntity suffers delay caused by the realization of the servers (e.g. distance related; FEC encoding etc.) along with some client specific processing. This is the total average latency effect of the TopologicalEntity";
        }
        leaf jitterCharacteristic {
            type string;
            config false;
            description "High frequency deviation from true periodicity of a signal and therefore a small high rate of change of transfer latency.
                Applies to TDM systems (and not packet).";
        }
        leaf wanderCharacteristic {
            type string;
            config false;
            description "Low frequency deviation from true periodicity of a signal and therefore a small low rate of change of transfer latency.
                Applies to TDM systems (and not packet).";
        }
        list queuingLatency {
            key 'latencyValue';
            config false;
            uses Tapi-TypeDefinitions:QueuingLatency;
            description "The effect on the latency of a queuing process. This only has significant effect for packet based systems and has a complex characteristic.";
        }
        description "A TopologicalEntity will suffer effects from the underlying physical realization related to the timing of the information passed by the TopologicalEntity.";
    }
    grouping TransferIntegrityPac {
        leaf errorCharacteristic {
            type string;
            config false;
            description "Describes the degree to which the signal propagated can be errored. 
                Applies to TDM systems as the errored signal will be propagated and not packet as errored packets will be discarded.";
        }
        leaf lossCharacteristic {
            type string;
            config false;
            description "Describes the acceptable characteristic of lost packets where loss may result from discard due to errors or overflow.
                Applies to packet systems and not TDM (as for TDM errored signals are propagated unless grossly errored and overflow/underflow turns into timing slips).";
        }
        leaf repeatDeliveryCharacteristic {
            type string;
            config false;
            description "Primarily applies to packet systems where a packet may be delivered more than once (in fault recovery for example). 
                It can also apply to TDM where several frames may be received twice due to switching in a system with a large differential propagation delay.";
        }
        leaf deliveryOrderCharacteristic {
            type string;
            config false;
            description "Describes the degree to which packets will be delivered out of sequence.
                Does not apply to TDM as the TDM protocols maintain strict order.";
        }
        leaf unavailableTimeCharacteristic {
            type string;
            config false;
            description "Describes the duration for which there may be no valid signal propagated.";
        }
        leaf serverIntegrityProcessCharacteristic {
            type string;
            config false;
            description "Describes the effect of any server integrity enhancement process on the characteristics of the TopologicalEntity.";
        }
        description "Transfer intergrity characteristic covers expected/specified/acceptable characteristic of degradation of the transfered signal.
            It includes all aspects of possible degradation of signal content as well as any damage of any form to the total TopologicalEntity and to the carried signals.
            Note that the statement is of total impact to the TopologicalEntity so any partial usage of the TopologicalEntity (e.g. a signal that does not use full capacity) will only suffer its portion of the impact.";
    }
    grouping TransferCapacityPac {
        container totalPotentialCapacity {
            config false;
            uses Tapi-TypeDefinitions:Capacity;
            description "An optimistic view of the capacity of the TopologicalEntity assuming that any shared capacity is available to be taken.";
        }
        container availableCapacity {
            config false;
            uses Tapi-TypeDefinitions:Capacity;
            description "Capacity available to be assigned.";
        }
        list capacityAssignedToUserView {
            key 'numberingRange';
            config false;
            uses Tapi-TypeDefinitions:Capacity;
            description "Capacity already assigned";
        }
        leaf capacityInteractionAlgorithm {
            type string;
            config false;
            description "A reference to an algorithm that describes how various chunks of allocated capacity interact (e.g. when shared)";
        }
        description "The TopologicalEntity derives capacity from the underlying realization. 
            A TopologicalEntity may be an abstraction and virtualization of a subset of the underlying capability offered in a view or may be directly reflecting the underlying realization.
            A TopologicalEntity may be directly used in the view or may be assigned to another view for use.
            The clients supported by a multi-layer TopologicalEntity may interact such that the resources used by one client may impact those available to another. This is derived from the LTP spec details.
            Represents the capacity available to user (client) along with client interaction and usage. 
            A TopologicalEntity may reflect one or more client protocols and one or more members for each profile.";
    }
    grouping ValidationPac {
        list validationMechanism {
            key 'validationRobustness';
            min-elements 1;
            config false;
            uses Tapi-TypeDefinitions:ValidationMechanism;
            description "Provides details of the specific validation mechanism(s) used to confirm the presence of an intended topologicalEntity.";
        }
        description "Validation covers the various adjacenct discovery and reachability verification protocols. Also may cover Information source and degree of integrity.";
    }
    grouping TeLink {
        leaf-list _node {
            type leafref {
                path '/Context/_topology/_node/uuid';
            }
            config false;
            min-elements 2;
            max-elements 2;
            description "none";
        }
        leaf-list _nodeEdgePoint {
            type leafref {
                path '/Context/_topology/_node/_ownedNodeEdgePoint/uuid';
            }
            config false;
            max-elements 2;
            description "none";
        }
        uses LocalClass;
        description "The Link object class models effective adjacency between two or more ForwardingDomains (FD). ";
    }
    grouping Path {
        list _telink {
            key 'localId';
            min-elements 1;
            config false;
            uses TeLink;
            description "none";
        }
        container _routingConstraint {
            config false;
            uses ConnectivityConstraint;
            description "none";
        }
        uses GlobalClass;
        description "Path is described by an ordered list of TE Links. A TE Link is defined by a pair of Node/NodeEdgePoint IDs. A Connection is realized by concatenating link resources (associated with a Link) and the lower-level connections (cross-connections) in the different nodes";
    }
    grouping GlobalClass {
        leaf uuid {
            type Tapi-TypeDefinitions:UniversalId;
            description "UUID: An identifier that is universally unique
                (consider in the context of Identifier: A property of an entity/role with a value that is unique within an identifier space, where the identifier space is itself globally unique, and immutable. An identifier carries no semantics with respect to the purpose or state of the entity)";
        }
        list name {
            key 'valueName';
            min-elements 1;
            uses Tapi-TypeDefinitions:NameAndValue;
            description "List of names. A property of an entity with a value that is unique in some namespace but may change during the life of the entity. A name carries no semantics with respect to the purpose of the entity.";
        }
        list label {
            key 'valueName';
            uses Tapi-TypeDefinitions:NameAndValue;
            description "List of labels.A property of an entity with a value that is not expected to be unique and is allowed to change. A label carries no semantics with respect to the purpose of the entity and has no effect on the entity behavior or state.";
        }
        description "The TAPI GlobalComponent serves as the super class for all TAPI entities that can be directly retrieved by their ID. As such, these are first class entities and their ID is expected to be globally unique. ";
    }
    grouping LocalClass {
        leaf localId {
            type string;
            description "none";
        }
        description "The TAPI GlobalComponent serves as the super class for all TAPI entities that can be directly retrieved by their ID. As such, these are first class entities and their ID is expected to be globally unique. ";
    }
    grouping AdminStatePac {
        leaf administrativeState {
            type Tapi-TypeDefinitions:AdministrativeState;
            description "none";
        }
        leaf operationalState {
            type Tapi-TypeDefinitions:OperationalState;
            description "none";
        }
        leaf lifecycleState {
            type Tapi-TypeDefinitions:LifecycleState;
            description "none";
        }
        description "Provides state attributes that are applicable to an entity that can be administered. Such an entity also has operational and lifecycle aspects.";
    }
    grouping LifecycleStatePac {
        leaf lifecycleState {
            type Tapi-TypeDefinitions:LifecycleState;
            description "none";
        }
        description "Provides state attributes for an entity that has lifeccycle aspects only.";
    }
    grouping OperationalStatePac {
        leaf operationalState {
            type Tapi-TypeDefinitions:OperationalState;
            description "none";
        }
        leaf lifecycleState {
            type Tapi-TypeDefinitions:LifecycleState;
            description "none";
        }
        description "Provides state attributes that are applicable to an entity that reflects operational aspects. Such an entity is expected to also have lifecycle aspects.";
    }
    grouping ConnectivityConstraint {
        leaf serviceType {
            type Tapi-TypeDefinitions:ServiceType;
            config false;
            description "none";
        }
        leaf serviceLevel {
            type string;
            config false;
            description "An abstract value the meaning of which is mutually agreed – typically represents metrics such as - Class of service, priority, resiliency, availability";
        }
        leaf-list serviceLayer {
            type Tapi-TypeDefinitions:LayerProtocolName;
            config false;
            description "none";
        }
        container requestedCapacity {
            config false;
            uses Tapi-TypeDefinitions:Capacity;
            description "none";
        }
        list costCharacteristic {
            key 'costAlgorithm';
            config false;
            uses Tapi-TypeDefinitions:CostCharacteristic;
            description "The list of costs where each cost relates to some aspect of the TopologicalEntity.";
        }
        list riskCharacteristic {
            key 'riskCharacteristicName';
            config false;
            uses Tapi-TypeDefinitions:RiskCharacteristic;
            description "A list of risk characteristics for consideration in an analysis of shared risk. Each element of the list represents a specific risk consideration.";
        }
        list latencyCharacteristic {
            key 'latencyValue';
            config false;
            uses Tapi-TypeDefinitions:QueuingLatency;
            description "The effect on the latency of a queuing process. This only has significant effect for packet based systems and has a complex characteristic.";
        }
        leaf-list includeTopology {
            type leafref {
                path '/Context/_topology/uuid';
            }
            config false;
            description "none";
        }
        leaf-list avoidTopology {
            type leafref {
                path '/Context/_topology/uuid';
            }
            config false;
            description "none";
        }
        leaf-list includePath {
            type leafref {
                path '/Context/_pathCompService/_path/uuid';
            }
            config false;
            description "none";
        }
        leaf-list excludePath {
            type leafref {
                path '/Context/_pathCompService/_path/uuid';
            }
            config false;
            description "none";
        }
        description "none";
    }
    grouping PathOptimizationConstraint {
        leaf trafficInterruption {
            type Tapi-TypeDefinitions:DirectiveValue;
            config false;
            description "none";
        }
        description "none";
    }
    grouping PathObjectiveFunction {
        leaf bandwidthOptimization {
            type Tapi-TypeDefinitions:DirectiveValue;
            config false;
            description "none";
        }
        leaf concurrentPaths {
            type Tapi-TypeDefinitions:DirectiveValue;
            config false;
            description "none";
        }
        leaf costOptimization {
            type Tapi-TypeDefinitions:DirectiveValue;
            config false;
            description "none";
        }
        leaf linkUtilization {
            type Tapi-TypeDefinitions:DirectiveValue;
            config false;
            description "none";
        }
        leaf resourceSharing {
            type Tapi-TypeDefinitions:DirectiveValue;
            config false;
            description "none";
        }
        description "none";
    }
    grouping TimeRange {
        leaf endTime {
            type Tapi-TypeDefinitions:DateAndTime;
            description "none";
        }
        leaf startTime {
            type Tapi-TypeDefinitions:DateAndTime;
            description "none";
        }
        description "none";
    }
    grouping VirtualNetworkService {
        leaf _topology {
            type leafref {
                path '/Context/_topology/uuid';
            }
            config false;
            description "none";
        }
        list _servicePort {
            key 'localId';
            min-elements 2;
            uses VirtualNetworkServicePort;
            description "none";
        }
        container _vnwConstraint {
            uses VirtualNetworkConstraint;
            description "none";
        }
        container _schedule {
            uses TimeRange;
            description "none";
        }
        container _state {
            uses AdminStatePac;
            description "none";
        }
        leaf-list layerProtocolName {
            type Tapi-TypeDefinitions:LayerProtocolName;
            min-elements 1;
            description "none";
        }
        uses GlobalClass;
        description "The ForwardingConstruct (FC) object class models enabled potential for forwarding between two or more LTPs and like the LTP supports any transport protocol including all circuit and packet forms.
            At the lowest level of recursion, a FC represents a cross-connection within an NE.";
    }
    grouping VirtualNetworkServicePort {
        leaf _serviceEndPoint {
            type leafref {
                path '/Context/_serviceEndPoint/uuid';
            }
            config false;
            description "none";
        }
        leaf role {
            type Tapi-TypeDefinitions:PortRole;
            config false;
            description "Each EP of the FC has a role (e.g., working, protection, protected, symmetric, hub, spoke, leaf, root)  in the context of the FC with respect to the FC function. ";
        }
        leaf direction {
            type Tapi-TypeDefinitions:PortDirection;
            config false;
            description "The orientation of defined flow at the EndPoint.";
        }
        leaf serviceLayer {
            type Tapi-TypeDefinitions:LayerProtocolName;
            config false;
            description "none";
        }
        uses LocalClass;
        description "The association of the FC to LTPs is made via EndPoints.
            The EndPoint (EP) object class models the access to the FC function. 
            The traffic forwarding between the associated EPs of the FC depends upon the type of FC and may be associated with FcSwitch object instances.  
            In cases where there is resilience the EndPoint may convey the resilience role of the access to the FC. 
            It can represent a protected (resilient/reliable) point or a protecting (unreliable working or protection) point.
            The EP replaces the Protection Unit of a traditional protection model. 
            The ForwadingConstruct can be considered as a component and the EndPoint as a Port on that component";
    }
    grouping VirtualNetworkConstraint {
        leaf serviceType {
            type Tapi-TypeDefinitions:ServiceType;
            description "none";
        }
        leaf serviceLevel {
            type string;
            description "An abstract value the meaning of which is mutually agreed – typically represents metrics such as - Class of service, priority, resiliency, availability";
        }
        leaf-list serviceLayer {
            type Tapi-TypeDefinitions:LayerProtocolName;
            description "none";
        }
        container requestedCapacity {
            uses Tapi-TypeDefinitions:Capacity;
            description "none";
        }
        list costCharacteristic {
            key 'costAlgorithm';
            uses Tapi-TypeDefinitions:CostCharacteristic;
            description "The list of costs where each cost relates to some aspect of the TopologicalEntity.";
        }
        list riskCharacteristic {
            key 'riskCharacteristicName';
            uses Tapi-TypeDefinitions:RiskCharacteristic;
            description "A list of risk characteristics for consideration in an analysis of shared risk. Each element of the list represents a specific risk consideration.";
        }
        list latencyCharacteristic {
            key 'latencyValue';
            uses Tapi-TypeDefinitions:QueuingLatency;
            description "The effect on the latency of a queuing process. This only has significant effect for packet based systems and has a complex characteristic.";
        }
        description "none";
    }
    grouping NotificationSubscriptionService {
        list _notification {
            key 'notificationId';
            config false;
            uses Notification;
            description "none";
        }
        container _subscriptionFilter {
            uses SubscriptionFilter;
            description "none";
        }
        leaf subscriptionState {
            type Tapi-TypeDefinitions:SubscriptionState;
            description "none";
        }
        leaf-list supportedNotificationTypes {
            type Tapi-TypeDefinitions:NotificationType;
            config false;
            min-elements 1;
            description "none";
        }
        leaf-list supportedObjectTypes {
            type Tapi-TypeDefinitions:ObjectType;
            config false;
            min-elements 1;
            description "none";
        }
        uses GlobalClass;
        description "none";
    }
    grouping SubscriptionFilter {
        leaf-list requestedNotificationTypes {
            type Tapi-TypeDefinitions:NotificationType;
            config false;
            description "none";
        }
        leaf-list requestedObjectTypes {
            type Tapi-TypeDefinitions:ObjectType;
            config false;
            description "none";
        }
        leaf-list requestedLayerProtocols {
            type Tapi-TypeDefinitions:LayerProtocolName;
            config false;
            description "none";
        }
        leaf-list requestedObjectIdentifier {
            type Tapi-TypeDefinitions:UniversalId;
            config false;
            description "none";
        }
        description "none";
    }
    grouping Notification {
        leaf notificationId {
            type Tapi-TypeDefinitions:UniversalId;
            description "none";
        }
        leaf notificationType {
            type Tapi-TypeDefinitions:NotificationType;
            description "none";
        }
        leaf targetObjectType {
            type Tapi-TypeDefinitions:ObjectType;
            description "none";
        }
        leaf targetObjectIdentifier {
            type Tapi-TypeDefinitions:UniversalId;
            description "none";
        }
        list targetObjectName {
            key 'valueName';
            min-elements 1;
            uses Tapi-TypeDefinitions:NameAndValue;
            description "none";
        }
        leaf eventTimeStamp {
            type Tapi-TypeDefinitions:DateAndTime;
            description "none";
        }
        leaf sourceIndicator {
            type Tapi-TypeDefinitions:SourceIndicator;
            description "none";
        }
        leaf layerProtocolName {
            type Tapi-TypeDefinitions:LayerProtocolName;
            description "none";
        }
        list changedAttributes {
            uses Tapi-TypeDefinitions:NameAndValueChange;
            description "none";
        }
        list additionalInfo {
            key 'valueName';
            uses Tapi-TypeDefinitions:NameAndValue;
            description "none";
        }
        leaf additionalText {
            type string;
            description "none";
        }
        description "none";
    }
    notification Notification {
        uses Notification;
    }
    grouping PathComputationService {
        list _path {
            key 'uuid';
            min-elements 1;
            config false;
            uses Path;
            description "none";
        }
        list _servicePort {
            key 'localId';
            min-elements 2;
            max-elements 2;
            uses PathCompServicePort;
            description "none";
        }
        container _routingConstraint {
            uses ConnectivityConstraint;
            description "none";
        }
        container _objectiveFunction {
            uses PathObjectiveFunction;
            description "none";
        }
        container _optimizationConstraint {
            uses PathOptimizationConstraint;
            description "none";
        }
        uses GlobalClass;
        description "none";
    }
    grouping PathCompServicePort {
        leaf _serviceEndPoint {
            type leafref {
                path '/Context/_serviceEndPoint/uuid';
            }
            config false;
            description "none";
        }
        leaf role {
            type Tapi-TypeDefinitions:PortRole;
            config false;
            description "Each EP of the FC has a role (e.g., working, protection, protected, symmetric, hub, spoke, leaf, root)  in the context of the FC with respect to the FC function. ";
        }
        leaf direction {
            type Tapi-TypeDefinitions:PortDirection;
            config false;
            description "The orientation of defined flow at the EndPoint.";
        }
        leaf serviceLayer {
            type Tapi-TypeDefinitions:LayerProtocolName;
            config false;
            description "none";
        }
        uses LocalClass;
        description "The association of the FC to LTPs is made via EndPoints.
            The EndPoint (EP) object class models the access to the FC function. 
            The traffic forwarding between the associated EPs of the FC depends upon the type of FC and may be associated with FcSwitch object instances.  
            In cases where there is resilience the EndPoint may convey the resilience role of the access to the FC. 
            It can represent a protected (resilient/reliable) point or a protecting (unreliable working or protection) point.
            The EP replaces the Protection Unit of a traditional protection model. 
            The ForwadingConstruct can be considered as a component and the EndPoint as a Port on that component";
    }
}
