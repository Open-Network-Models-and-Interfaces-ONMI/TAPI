module Tapi-Interfaces-TopologyService {
    namespace "urn:ONF:Tapi-Interfaces-TopologyService";
    prefix Tapi-Interfaces-TopologyService;
    import Tapi-ObjectClasses {
        prefix Tapi-ObjectClasses;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-08 {
        description "Latest revision";
        reference "RFC 6020 and RFC 6087";
    }
    rpc getTopologyDetails {
        description "none";
        input {
            leaf topologyIdOrName {
                type string;
                description "none";
            }
        }
        output {
            container topology {
                uses Tapi-ObjectClasses:Topology;
                description "none";
            }
        }
    }
    rpc getNodeDetails {
        description "none";
        input {
            leaf topologyIdOrName {
                type string;
                description "none";
            }
            leaf nodeIdOrName {
                type string;
                description "none";
            }
        }
        output {
            container node {
                uses Tapi-ObjectClasses:Node;
                description "none";
            }
        }
    }
    rpc getNodeEdgePointDetails {
        description "none";
        input {
            leaf topologyIdOrName {
                type string;
                description "none";
            }
            leaf nodeIdOrName {
                type string;
                description "none";
            }
            leaf epIdOrName {
                type string;
                description "none";
            }
        }
        output {
            container nodeEdgePoint {
                uses Tapi-ObjectClasses:NodeEdgePoint;
                description "none";
            }
        }
    }
    rpc getLinkDetails {
        description "none";
        input {
            leaf topologyIdOrName {
                type string;
                description "none";
            }
            leaf linkIdOrName {
                type string;
                description "none";
            }
        }
        output {
            container link {
                uses Tapi-ObjectClasses:Link;
                description "none";
            }
        }
    }
    rpc getTopologyList {
        description "none";
        output {
            list topology {
                uses Tapi-ObjectClasses:Topology;
                description "none";
            }
        }
    }
}
