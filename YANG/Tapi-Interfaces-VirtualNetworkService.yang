module Tapi-Interfaces-VirtualNetworkService {
    namespace "urn:ONF:Tapi-Interfaces-VirtualNetworkService";
    prefix Tapi-Interfaces-VirtualNetworkService;
    import Tapi-ObjectClasses {
        prefix Tapi-ObjectClasses;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-08 {
        description "Latest revision";
        reference "RFC 6020 and RFC 6087";
    }
    rpc createVirtualNetworkService {
        description "none";
        input {
            list servicePort {
                min-elements 2;
                uses Tapi-ObjectClasses:VirtualNetworkServicePort;
                description "none";
            }
            container vnwConstraint {
                uses Tapi-ObjectClasses:VirtualNetworkConstraint;
                description "none";
            }
            container connSchedule {
                uses Tapi-ObjectClasses:TimeRange;
                description "none";
            }
        }
        output {
            container vnwService {
                uses Tapi-ObjectClasses:VirtualNetworkService;
                description "none";
            }
        }
    }
    rpc deleteVirtualNetworkService {
        description "none";
        input {
            leaf serviceIdOrName {
                type string;
                description "none";
            }
        }
        output {
            container vnwService {
                uses Tapi-ObjectClasses:VirtualNetworkService;
                description "none";
            }
        }
    }
    rpc getVirtualNetworkServiceDetails {
        description "none";
        input {
            leaf serviceIdOrName {
                type string;
                description "none";
            }
        }
        output {
            container vnwService {
                uses Tapi-ObjectClasses:VirtualNetworkService;
                description "none";
            }
        }
    }
    rpc getVirtualNetworkServiceList {
        description "none";
        output {
            list vnwService {
                uses Tapi-ObjectClasses:VirtualNetworkService;
                description "none";
            }
        }
    }
}
