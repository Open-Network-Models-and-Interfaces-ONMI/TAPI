module tapi-eth {
    namespace "urn:onf:otcc:yang:tapi-eth";
    prefix tapi-eth;
    import tapi-common {
        prefix tapi-common;
    }
    import tapi-topology {
        prefix tapi-topology;
    }
    import tapi-connectivity {
        prefix tapi-connectivity;
    }
    import tapi-oam {
        prefix tapi-oam;
    }
    import tapi-fm {
        prefix tapi-fm;
    }
    organization "ONF OTCC (Open Transport Configuration & Control) Project";
    contact "
         Project Web: <https://wiki.opennetworking.org/display/OTCC/TAPI>
         Project List: <mailto:transport-api@opennetworking.org>
         Editor: Karthik Sethuraman
                 <mailto:karthik.sethuraman@necam.com>";
    description "
        This module contains TAPI ETH Model definitions.
        Source: TapiEth.uml
        Copyright (c) 2018 Open Networking Foundation (ONF). All rights reserved.
        License: This module is distributed under the Apache License 2.0
        - The TAPI YANG models included in this TAPI release are a *normative* part of the TAPI SDK.
        - The YANG specifications have been generated from the corresponding UML model using the [ONF EAGLE UML2YANG mapping tool]
        <https://github.com/OpenNetworkingFoundation/EagleUmlYang>
        and further edited manually to comply with the [ONF IISOMI UML2YANG mapping guidelines]
        <https://wiki.opennetworking.org/display/OIMT/UML+-+YANG+Guidelines>
        - Status of YANG model artifacts can be determined by referring to the corresponding UML artifacts.
        As described in the UML models, some artifacts are considered *experimental*, and thus the corresponding YANG artifacts.
        - The ONF TAPI release process does not guarantee backward compatibility of YANG models across major versions of TAPI releases.
        The YANG model backward compatibility criteria are outlined in section 11 of <https://tools.ietf.org/html/rfc7950>.
        YANG models included in this release may not be backward compatible with previous TAPI releases.";
    revision 2019-03-31 {
        description "ONF Transport API version 2.2-RC1.
                   Changes included in this TAPI release (v2.2) are listed in
                  <https://github.com/OpenNetworkingFoundation/TAPI/blob/develop/CHANGE_LOG/change-log.2.2.md>";
        reference "ONF-TR-527, ONF-TR-512, ONF-TR-531, RFC 7950, RFC 6087 and ONF TAPI UML model
                  <https://github.com/OpenNetworkingFoundation/TAPI/tree/v2.2.0/UML>";
    }
    revision 2018-12-10 {
        description "ONF Transport API version 2.1.1.
                   Changes included in this TAPI release (v2.1.1) are listed in
                  <https://github.com/OpenNetworkingFoundation/TAPI/blob/develop/CHANGE_LOG/change-log.2.1.1.md>";
        reference "ONF-TR-527, ONF-TR-512, ONF-TR-531, RFC 7950, RFC 6087 and ONF TAPI UML model
                  <https://github.com/OpenNetworkingFoundation/TAPI/tree/v2.1.1/UML>";
    }
    revision 2018-10-16 {
        description "ONF Transport API version 2.1.0.
                   Changes included in this TAPI release (v2.1.0) are listed in
                  <https://github.com/OpenNetworkingFoundation/TAPI/blob/develop/CHANGE_LOG/change-log.2.1.0.md>";
        reference "ONF-TR-527, ONF-TR-512, ONF-TR-531, RFC 7950, RFC 6087 and ONF TAPI UML model
                  <https://github.com/OpenNetworkingFoundation/TAPI/tree/v2.1.0/UML>";
    }
    revision 2018-03-07 {
        description "ONF Transport API version 2.0.2
        This YANG module has been generated from the TAPI UML Model using the IISOMI-Eagle xmi2yang mapping tool.
        Changes in this revision: <https://github.com/OpenNetworkingFoundation/TAPI/blob/develop/CHANGE_LOG/change-log.2.0.2.md>";
        reference "ONF-TR-527, ONF-TR-512, ONF-TR-531, RFC 6020, RFC 6087 and ONF TAPI UML model
                  <https://github.com/OpenNetworkingFoundation/TAPI/tree/v2.0.2/UML>";
    }
    revision 2018-02-16 {
        description "ONF Transport API version 2.0.1
        This YANG module has been generated from the TAPI UML Model using the IISOMI-Eagle xmi2yang mapping tool.
        Changes in this revision: <https://github.com/OpenNetworkingFoundation/TAPI/blob/develop/CHANGE_LOG/change-log.2.0.1.md>";
        reference "ONF-TR-527, ONF-TR-512, ONF-TR-531, RFC 6020, RFC 6087 and ONF TAPI UML model
                  <https://github.com/OpenNetworkingFoundation/TAPI/tree/v2.0.1/UML>";
    }
    revision 2018-01-02 {
        description "ONF Transport API version 2.0.0
        This YANG module has been generated from the TAPI UML Model using the IISOMI-Eagle xmi2yang mapping tool.
        Changes in this revision: <https://github.com/OpenNetworkingFoundation/TAPI/blob/develop/CHANGE_LOG/change-log.2.0.0.md>";
        reference "ONF-TR-527, ONF-TR-512, ONF-TR-531, RFC 6020, RFC 6087 and ONF TAPI UML model
                  <https://github.com/OpenNetworkingFoundation/TAPI/tree/v2.0.0/UML>";
    }
    augment "/tapi-common:context/tapi-topology:topology-context/tapi-topology:topology/tapi-topology:node/tapi-topology:owned-node-edge-point/tapi-connectivity:cep-list/tapi-connectivity:connection-end-point" {
        container eth-connection-end-point-spec {
            uses eth-connection-end-point-spec;
            description "Augments the base LayerProtocol information in ConnectionEndPoint with ETH-specific information";
        }
        description "Augments the base LayerProtocol information in ConnectionEndPoint with ETH-specific information";
    }
    augment "/tapi-common:context/tapi-oam:oam-context/tapi-oam:oam-job" {
        container eth-loopback-job {
            uses eth-loopback-job;
            description "none";
        }
        description "none";
    }
    augment "/tapi-common:context/tapi-oam:oam-context/tapi-oam:meg" {
        container eth-meg-spec {
            uses eth-meg-spec;
            description "none";
        }
        description "none";
    }
    augment "/tapi-common:context/tapi-oam:oam-context/tapi-oam:meg/tapi-oam:mep" {
        container eth-mep-spec {
            uses eth-mep-spec;
            description "none";
        }
        description "none";
    }
    augment "/tapi-common:context/tapi-oam:oam-context/tapi-oam:meg/tapi-oam:mip" {
        container eth-mip-spec {
            uses eth-mip-spec;
            description "none";
        }
        description "none";
    }
    augment "/tapi-common:context/tapi-oam:oam-context/tapi-oam:oam-job" {
        container eth-pro-active-single-ended-measurement-job {
            uses eth-pro-active-single-ended-measurement-job;
            description "none";
        }
        description "none";
    }
    augment "/tapi-common:context/tapi-oam:oam-context/tapi-oam:oam-job" {
        container eth-link-trace-job {
            uses eth-link-trace-job;
            description "none";
        }
        description "none";
    }
    augment "/tapi-common:context/tapi-oam:oam-context/tapi-oam:oam-job" {
        container eth-test-job {
            uses eth-test-job;
            description "none";
        }
        description "none";
    }
    augment "/tapi-common:context/tapi-oam:oam-context/tapi-oam:oam-job" {
        container eth-pro-active-dual-ended-measurement-job {
            uses eth-pro-active-dual-ended-measurement-job;
            description "none";
        }
        description "none";
    }
    augment "/tapi-common:context/tapi-oam:oam-context/tapi-oam:oam-job/tapi-oam:current-data" {
        container eth-pro-active-dm-performance-data {
            uses eth-pro-active-dm-performance-data;
            description "none";
        }
        description "none";
    }
    augment "/tapi-common:context/tapi-oam:oam-context/tapi-oam:oam-job/tapi-oam:current-data/tapi-oam:history-data" {
        container eth-pro-active-dm-performance-data {
            uses eth-pro-active-dm-performance-data;
            description "none";
        }
        description "none";
    }
    augment "/tapi-common:context/tapi-oam:oam-context/tapi-oam:oam-job/tapi-oam:current-data" {
        container eth-pro-active-lm-performance-data {
            uses eth-pro-active-lm-performance-data;
            description "none";
        }
        description "none";
    }
    augment "/tapi-common:context/tapi-oam:oam-context/tapi-oam:oam-job/tapi-oam:current-data/tapi-oam:history-data" {
        container eth-pro-active-lm-performance-data {
            uses eth-pro-active-lm-performance-data;
            description "none";
        }
        description "none";
    }
    augment "/tapi-common:context/tapi-oam:oam-context/tapi-oam:oam-job/tapi-oam:current-data" {
        container eth-on-demand-dm-performance-data {
            uses eth-on-demand-dm-performance-data;
            description "none";
        }
        description "none";
    }
    augment "/tapi-common:context/tapi-oam:oam-context/tapi-oam:oam-job/tapi-oam:current-data" {
        container eth-on-demand-1-lm-performance-data {
            uses eth-on-demand-1-lm-performance-data;
            description "none";
        }
        description "none";
    }
    augment "/tapi-common:context/tapi-oam:oam-context/tapi-oam:oam-job/tapi-oam:current-data" {
        container eth-on-demand-1-dm-performance-data {
            uses eth-on-demand-1-dm-performance-data;
            description "none";
        }
        description "none";
    }
    augment "/tapi-common:context/tapi-oam:oam-context/tapi-oam:oam-job/tapi-oam:current-data" {
        container eth-pro-active-1-dm-performance-data {
            uses eth-pro-active-1-dm-performance-data;
            description "none";
        }
        description "none";
    }
    augment "/tapi-common:context/tapi-oam:oam-context/tapi-oam:oam-job/tapi-oam:current-data/tapi-oam:history-data" {
        container eth-pro-active-1-dm-performance-data {
            uses eth-pro-active-1-dm-performance-data;
            description "none";
        }
        description "none";
    }
    augment "/tapi-common:context/tapi-oam:oam-context/tapi-oam:oam-job/tapi-oam:current-data" {
        container eth-pro-active-1-lm-performance-data {
            uses eth-pro-active-1-lm-performance-data;
            description "none";
        }
        description "none";
    }
    augment "/tapi-common:context/tapi-oam:oam-context/tapi-oam:oam-job/tapi-oam:current-data/tapi-oam:history-data" {
        container eth-pro-active-1-lm-performance-data {
            uses eth-pro-active-1-lm-performance-data;
            description "none";
        }
        description "none";
    }
    augment "/tapi-common:context/tapi-oam:oam-context/tapi-oam:oam-job" {
        container eth-on-demand-dual-ended-measurement-job {
            uses eth-on-demand-dual-ended-measurement-job;
            description "none";
        }
        description "none";
    }
    augment "/tapi-common:context/tapi-oam:oam-context/tapi-oam:oam-job" {
        container eth-on-demand-single-ended-measurement-job {
            uses eth-on-demand-single-ended-measurement-job;
            description "none";
        }
        description "none";
    }
    augment "/tapi-common:context/tapi-oam:oam-context/tapi-oam:oam-job/tapi-oam:current-data/tapi-oam:history-data" {
        container eth-on-demand-1-dm-performance-data {
            uses eth-on-demand-1-dm-performance-data;
            description "none";
        }
        description "none";
    }
    augment "/tapi-common:context/tapi-oam:oam-context/tapi-oam:oam-job/tapi-oam:current-data/tapi-oam:history-data" {
        container eth-on-demand-1-lm-performance-data {
            uses eth-on-demand-1-lm-performance-data;
            description "none";
        }
        description "none";
    }
    augment "/tapi-common:context/tapi-oam:oam-context/tapi-oam:oam-job/tapi-oam:current-data/tapi-oam:history-data" {
        container eth-on-demand-dm-performance-data {
            uses eth-on-demand-dm-performance-data;
            description "none";
        }
        description "none";
    }
    augment "/tapi-common:context/tapi-oam:oam-context/tapi-oam:oam-job/tapi-oam:current-data" {
        container eth-on-demand-lm-performance-data {
            uses eth-on-demand-lm-performance-data;
            description "none";
        }
        description "none";
    }
    augment "/tapi-common:context/tapi-oam:oam-context/tapi-oam:oam-job/tapi-oam:current-data/tapi-oam:history-data" {
        container eth-on-demand-lm-performance-data {
            uses eth-on-demand-lm-performance-data;
            description "none";
        }
        description "none";
    }
    augment "/tapi-common:context/tapi-oam:oam-context/tapi-oam:oam-job/tapi-oam:current-data" {
        container eth-link-trace-result-data {
            uses eth-link-trace-result-data;
            description "none";
        }
        description "none";
    }
    augment "/tapi-common:context/tapi-oam:oam-context/tapi-oam:oam-job/tapi-oam:current-data" {
        container eth-test-result-data {
            uses eth-test-result-data;
            description "none";
        }
        description "none";
    }
    augment "/tapi-common:context/tapi-oam:oam-context/tapi-oam:oam-job/tapi-oam:current-data" {
        container eth-loopback-result-data {
            uses eth-loopback-result-data;
            description "none";
        }
        description "none";
    }
    augment "/tapi-oam:create-oam-job/tapi-oam:input" {
        container eth-loopback-job {
            uses eth-loopback-job;
            description "none";
        }
        description "none";
    }
    augment "/tapi-oam:create-oam-job/tapi-oam:input" {
        container eth-link-trace-job {
            uses eth-link-trace-job;
            description "none";
        }
        description "none";
    }
    augment "/tapi-oam:create-oam-job/tapi-oam:input" {
        container eth-test-job {
            uses eth-test-job;
            description "none";
        }
        description "none";
    }
    augment "/tapi-oam:create-oam-job/tapi-oam:input" {
        container eth-pro-active-dual-ended-measurement-job {
            uses eth-pro-active-dual-ended-measurement-job;
            description "none";
        }
        description "none";
    }
    augment "/tapi-oam:create-oam-job/tapi-oam:input" {
        container eth-pro-active-single-ended-measurement-job {
            uses eth-pro-active-single-ended-measurement-job;
            description "none";
        }
        description "none";
    }
    augment "/tapi-oam:create-oam-job/tapi-oam:input" {
        container eth-on-demand-single-ended-measurement-job {
            uses eth-on-demand-single-ended-measurement-job;
            description "none";
        }
        description "none";
    }
    augment "/tapi-oam:create-oam-job/tapi-oam:input" {
        container eth-on-demand-dual-ended-measurement-job {
            uses eth-on-demand-dual-ended-measurement-job;
            description "none";
        }
        description "none";
    }
    augment "/tapi-oam:update-oam-job/tapi-oam:input" {
        container eth-loopback-job {
            uses eth-loopback-job;
            description "none";
        }
        description "none";
    }
    augment "/tapi-oam:update-oam-job/tapi-oam:input" {
        container eth-link-trace-job {
            uses eth-link-trace-job;
            description "none";
        }
        description "none";
    }
    augment "/tapi-oam:update-oam-job/tapi-oam:input" {
        container eth-test-job {
            uses eth-test-job;
            description "none";
        }
        description "none";
    }
    augment "/tapi-oam:update-oam-job/tapi-oam:input" {
        container eth-pro-active-dual-ended-measurement-job {
            uses eth-pro-active-dual-ended-measurement-job;
            description "none";
        }
        description "none";
    }
    augment "/tapi-oam:update-oam-job/tapi-oam:input" {
        container eth-pro-active-single-ended-measurement-job {
            uses eth-pro-active-single-ended-measurement-job;
            description "none";
        }
        description "none";
    }
    augment "/tapi-oam:update-oam-job/tapi-oam:input" {
        container eth-on-demand-dual-ended-measurement-job {
            uses eth-on-demand-dual-ended-measurement-job;
            description "none";
        }
        description "none";
    }
    augment "/tapi-oam:get-oam-job/tapi-oam:output/tapi-oam:oam-job" {
        container eth-loopback-job {
            uses eth-loopback-job;
            description "none";
        }
        description "none";
    }
    augment "/tapi-oam:get-oam-job/tapi-oam:output/tapi-oam:oam-job" {
        container eth-link-trace-job {
            uses eth-link-trace-job;
            description "none";
        }
        description "none";
    }
    augment "/tapi-oam:get-oam-job/tapi-oam:output/tapi-oam:oam-job" {
        container eth-pro-active-dual-ended-measurement-job {
            uses eth-pro-active-dual-ended-measurement-job;
            description "none";
        }
        description "none";
    }
    augment "/tapi-oam:get-oam-job/tapi-oam:output/tapi-oam:oam-job" {
        container eth-pro-active-single-ended-measurement-job {
            uses eth-pro-active-single-ended-measurement-job;
            description "none";
        }
        description "none";
    }
    augment "/tapi-oam:get-oam-job/tapi-oam:output/tapi-oam:oam-job" {
        container eth-on-demand-single-ended-measurement-job {
            uses eth-on-demand-single-ended-measurement-job;
            description "none";
        }
        description "none";
    }
    augment "/tapi-oam:get-oam-job/tapi-oam:output/tapi-oam:oam-job" {
        container eth-on-demand-dual-ended-measurement-job {
            uses eth-on-demand-dual-ended-measurement-job;
            description "none";
        }
        description "none";
    }
    augment "/tapi-oam:get-oam-job-list/tapi-oam:output/tapi-oam:oam-job" {
        container eth-loopback-job {
            uses eth-loopback-job;
            description "none";
        }
        description "none";
    }
    augment "/tapi-oam:get-oam-job-list/tapi-oam:output/tapi-oam:oam-job" {
        container eth-test-job {
            uses eth-test-job;
            description "none";
        }
        description "none";
    }
    augment "/tapi-oam:get-oam-job-list/tapi-oam:output/tapi-oam:oam-job" {
        container eth-pro-active-dual-ended-measurement-job {
            uses eth-pro-active-dual-ended-measurement-job;
            description "none";
        }
        description "none";
    }
    augment "/tapi-oam:get-oam-job-list/tapi-oam:output/tapi-oam:oam-job" {
        container eth-on-demand-single-ended-measurement-job {
            uses eth-on-demand-single-ended-measurement-job;
            description "none";
        }
        description "none";
    }
    augment "/tapi-oam:get-oam-job-list/tapi-oam:output/tapi-oam:oam-job" {
        container eth-on-demand-dual-ended-measurement-job {
            uses eth-on-demand-dual-ended-measurement-job;
            description "none";
        }
        description "none";
    }
    augment "/tapi-common:context/tapi-oam:oam-context/tapi-oam:oam-service/tapi-oam:oam-service-point" {
        container eth-oam-mep-service-point {
            uses eth-oam-mep-service-point;
            description "none";
        }
        description "none";
    }
    augment "/tapi-common:context/tapi-oam:oam-context/tapi-oam:oam-service/tapi-oam:oam-service-point" {
        container eth-oam-mip-service-point {
            uses eth-oam-mip-service-point;
            description "none";
        }
        description "none";
    }
    augment "/tapi-common:context/tapi-oam:oam-context/tapi-oam:oam-service" {
        container eth-oam-service {
            uses eth-oam-service;
            description "none";
        }
        description "none";
    }
    augment "/tapi-common:context/tapi-oam:oam-context/tapi-oam:oam-job/tapi-oam:current-data" {
        container eth-pro-active-1-dm-source-performance-data {
            uses eth-pro-active-1-dm-source-performance-data;
            description "none";
        }
        description "none";
    }
    augment "/tapi-common:context/tapi-oam:oam-context/tapi-oam:oam-job/tapi-oam:current-data/tapi-oam:history-data" {
        container eth-pro-active-1-dm-source-performance-data {
            uses eth-pro-active-1-dm-source-performance-data;
            description "none";
        }
        description "none";
    }
    augment "/tapi-common:context/tapi-oam:oam-context/tapi-oam:oam-job/tapi-oam:current-data" {
        container eth-pro-active-1-lm-source-performance-data {
            uses eth-pro-active-1-lm-source-performance-data;
            description "none";
        }
        description "none";
    }
    augment "/tapi-common:context/tapi-oam:oam-context/tapi-oam:oam-job/tapi-oam:current-data/tapi-oam:history-data" {
        container eth-pro-active-1-lm-source-performance-data {
            uses eth-pro-active-1-lm-source-performance-data;
            description "none";
        }
        description "none";
    }
    augment "/tapi-common:context/tapi-oam:oam-context/tapi-oam:oam-job/tapi-oam:current-data" {
        container eth-on-demand-1-dm-source-performance-data {
            uses eth-on-demand-1-dm-source-performance-data;
            description "none";
        }
        description "none";
    }
    augment "/tapi-common:context/tapi-oam:oam-context/tapi-oam:oam-job/tapi-oam:current-data/tapi-oam:history-data" {
        container eth-on-demand-1-dm-source-performance-data {
            uses eth-on-demand-1-dm-source-performance-data;
            description "none";
        }
        description "none";
    }
    augment "/tapi-common:context/tapi-oam:oam-context/tapi-oam:oam-job/tapi-oam:current-data" {
        container eth-on-demand-1-lm-source-performance-data {
            uses eth-on-demand-1-lm-source-performance-data;
            description "none";
        }
        description "none";
    }
    augment "/tapi-common:context/tapi-oam:oam-context/tapi-oam:oam-job/tapi-oam:current-data/tapi-oam:history-data" {
        container eth-on-demand-1-lm-source-performance-data {
            uses eth-on-demand-1-lm-source-performance-data;
            description "none";
        }
        description "none";
    }
    augment "/tapi-common:context/tapi-connectivity:connectivity-context/tapi-connectivity:connectivity-service/tapi-connectivity:end-point" {
        container eth-connectivity-service-end-point-spec {
            uses eth-connectivity-service-end-point-spec;
            description "none";
        }
        description "none";
    }
    augment "/tapi-common:context/tapi-common:service-interface-point" {
        container eth-service-inteface-point-spec {
            uses eth-service-inteface-point-spec;
            description "none";
        }
        description "none";
    }
    augment "/tapi-common:get-service-interface-point-list/tapi-common:output/tapi-common:sip" {
        container eth-service-inteface-point-spec {
            uses eth-service-inteface-point-spec;
            description "none";
        }
        description "none";
    }
    augment "/tapi-connectivity:get-connectivity-service-list/tapi-connectivity:output/tapi-connectivity:service/tapi-connectivity:end-point" {
        container eth-connectivity-service-end-point-spec {
            uses eth-connectivity-service-end-point-spec;
            description "none";
        }
        description "none";
    }
    augment "/tapi-connectivity:get-connectivity-service-details/tapi-connectivity:output/tapi-connectivity:service/tapi-connectivity:end-point" {
        container eth-connectivity-service-end-point-spec {
            uses eth-connectivity-service-end-point-spec;
            description "none";
        }
        description "none";
    }
    augment "/tapi-connectivity:create-connectivity-service/tapi-connectivity:input/tapi-connectivity:end-point" {
        container eth-connectivity-service-end-point-spec {
            uses eth-connectivity-service-end-point-spec;
            description "none";
        }
        description "none";
    }
    augment "/tapi-connectivity:update-connectivity-service/tapi-connectivity:output/tapi-connectivity:service/tapi-connectivity:end-point" {
        container eth-connectivity-service-end-point-spec {
            uses eth-connectivity-service-end-point-spec;
            description "none";
        }
        description "none";
    }
    augment "/tapi-connectivity:update-connectivity-service/tapi-connectivity:input/tapi-connectivity:end-point" {
        container eth-connectivity-service-end-point-spec {
            uses eth-connectivity-service-end-point-spec;
            description "none";
        }
        description "none";
    }
    augment "/tapi-common:context/tapi-connectivity:connectivity-context/tapi-connectivity:connectivity-service" {
        container eth-connectivity-service {
            uses eth-connectivity-service;
            description "none";
        }
        description "none";
    }
    augment "/tapi-connectivity:get-connectivity-service-list/tapi-connectivity:output/tapi-connectivity:service" {
        container eth-connectivity-service {
            uses eth-connectivity-service;
            description "none";
        }
        description "none";
    }
    augment "/tapi-connectivity:get-connectivity-service-details/tapi-connectivity:output/tapi-connectivity:service" {
        container eth-connectivity-service {
            uses eth-connectivity-service;
            description "none";
        }
        description "none";
    }
    augment "/tapi-connectivity:update-connectivity-service/tapi-connectivity:output/tapi-connectivity:service" {
        container eth-connectivity-service {
            uses eth-connectivity-service;
            description "none";
        }
        description "none";
    }
    augment "/tapi-oam:get-oam-service/tapi-oam:output/tapi-oam:oam-service" {
        container eth-oam-service {
            uses eth-oam-service;
            description "none";
        }
        description "none";
    }
    augment "/tapi-oam:get-oam-service-list/tapi-oam:output/tapi-oam:oam-service" {
        container eth-oam-service {
            uses eth-oam-service;
            description "none";
        }
        description "none";
    }
    augment "/tapi-oam:create-oam-service/tapi-oam:input/tapi-oam:oam-service-point" {
        container eth-oam-service {
            uses eth-oam-service;
            description "none";
        }
        description "none";
    }
    augment "/tapi-oam:update-oam-service/tapi-oam:output/tapi-oam:oam-service" {
        container eth-oam-service {
            uses eth-oam-service;
            description "none";
        }
        description "none";
    }
    augment "/tapi-oam:create-oam-service/tapi-oam:output/tapi-oam:oam-service" {
        container eth-oam-service {
            uses eth-oam-service;
            description "none";
        }
        description "none";
    }
    augment "/tapi-oam:update-oam-service/tapi-oam:input/tapi-oam:oam-service-point" {
        container eth-oam-service {
            uses eth-oam-service;
            description "none";
        }
        description "none";
    }
    augment "/tapi-oam:get-oam-service/tapi-oam:output/tapi-oam:oam-service/tapi-oam:oam-service-point" {
        container eth-oam-mip-service-point {
            uses eth-oam-mip-service-point;
            description "none";
        }
        description "none";
    }
    augment "/tapi-oam:get-oam-service/tapi-oam:output/tapi-oam:oam-service/tapi-oam:oam-service-point" {
        container eth-oam-mep-service-point {
            uses eth-oam-mep-service-point;
            description "none";
        }
        description "none";
    }
    augment "/tapi-oam:get-oam-service-list/tapi-oam:output/tapi-oam:oam-service/tapi-oam:oam-service-point" {
        container eth-oam-mip-service-point {
            uses eth-oam-mip-service-point;
            description "none";
        }
        description "none";
    }
    augment "/tapi-oam:get-oam-service-list/tapi-oam:output/tapi-oam:oam-service/tapi-oam:oam-service-point" {
        container eth-oam-mep-service-point {
            uses eth-oam-mep-service-point;
            description "none";
        }
        description "none";
    }
    augment "/tapi-oam:create-oam-service/tapi-oam:output/tapi-oam:oam-service/tapi-oam:oam-service-point" {
        container eth-oam-mip-service-point {
            uses eth-oam-mip-service-point;
            description "none";
        }
        description "none";
    }
    augment "/tapi-oam:create-oam-service/tapi-oam:output/tapi-oam:oam-service/tapi-oam:oam-service-point" {
        container eth-oam-mep-service-point {
            uses eth-oam-mep-service-point;
            description "none";
        }
        description "none";
    }
    augment "/tapi-oam:update-oam-service/tapi-oam:output/tapi-oam:oam-service/tapi-oam:oam-service-point" {
        container eth-oam-mip-service-point {
            uses eth-oam-mip-service-point;
            description "none";
        }
        description "none";
    }
    augment "/tapi-oam:get-oam-service-point/tapi-oam:output/tapi-oam:oam-service-point" {
        container eth-oam-mep-service-point {
            uses eth-oam-mep-service-point;
            description "none";
        }
        description "none";
    }
    augment "/tapi-oam:get-oam-service-point/tapi-oam:output/tapi-oam:oam-service-point" {
        container eth-oam-mip-service-point {
            uses eth-oam-mip-service-point;
            description "none";
        }
        description "none";
    }
    augment "/tapi-oam:create-oam-service-point/tapi-oam:output/tapi-oam:oam-service-point" {
        container eth-oam-mep-service-point {
            uses eth-oam-mep-service-point;
            description "none";
        }
        description "none";
    }
    augment "/tapi-oam:create-oam-service-point/tapi-oam:output/tapi-oam:oam-service-point" {
        container eth-oam-mip-service-point {
            uses eth-oam-mip-service-point;
            description "none";
        }
        description "none";
    }
    augment "/tapi-oam:update-oam-service-point/tapi-oam:output/tapi-oam:oam-service-point" {
        container eth-oam-mep-service-point {
            uses eth-oam-mep-service-point;
            description "none";
        }
        description "none";
    }
    augment "/tapi-oam:update-oam-service-point/tapi-oam:output/tapi-oam:oam-service-point" {
        container eth-oam-mip-service-point {
            uses eth-oam-mip-service-point;
            description "none";
        }
        description "none";
    }
    augment "/tapi-oam:get-meg/tapi-oam:output/tapi-oam:meg" {
        container eth-meg-spec {
            uses eth-meg-spec;
            description "none";
        }
        description "none";
    }
    augment "/tapi-oam:get-meg/tapi-oam:output/tapi-oam:meg/tapi-oam:mep" {
        container eth-mep-spec {
            uses eth-mep-spec;
            description "none";
        }
        description "none";
    }
    augment "/tapi-oam:get-meg/tapi-oam:output/tapi-oam:meg/tapi-oam:mip" {
        container eth-mip-spec {
            uses eth-mip-spec;
            description "none";
        }
        description "none";
    }
    augment "/tapi-oam:create-oam-job/tapi-oam:output/tapi-oam:oam-job" {
        container eth-link-trace-job {
            uses eth-link-trace-job;
            description "none";
        }
        description "none";
    }
    augment "/tapi-oam:create-oam-job/tapi-oam:output/tapi-oam:oam-job" {
        container eth-loopback-job {
            uses eth-loopback-job;
            description "none";
        }
        description "none";
    }
    augment "/tapi-oam:create-oam-job/tapi-oam:output/tapi-oam:oam-job" {
        container eth-test-job {
            uses eth-test-job;
            description "none";
        }
        description "none";
    }
    augment "/tapi-oam:update-oam-job/tapi-oam:output/tapi-oam:oam-job" {
        container eth-loopback-job {
            uses eth-loopback-job;
            description "none";
        }
        description "none";
    }
    augment "/tapi-oam:update-oam-job/tapi-oam:output/tapi-oam:oam-job" {
        container eth-link-trace-job {
            uses eth-link-trace-job;
            description "none";
        }
        description "none";
    }
    augment "/tapi-oam:create-oam-job/tapi-oam:output/tapi-oam:oam-job" {
        container eth-on-demand-dual-ended-measurement-job {
            uses eth-on-demand-dual-ended-measurement-job;
            description "none";
        }
        description "none";
    }
    augment "/tapi-oam:create-oam-job/tapi-oam:output/tapi-oam:oam-job" {
        container eth-pro-active-dual-ended-measurement-job {
            uses eth-pro-active-dual-ended-measurement-job;
            description "none";
        }
        description "none";
    }
    augment "/tapi-oam:create-oam-job/tapi-oam:output/tapi-oam:oam-job" {
        container eth-pro-active-single-ended-measurement-job {
            uses eth-pro-active-single-ended-measurement-job;
            description "none";
        }
        description "none";
    }
    augment "/tapi-oam:create-oam-job/tapi-oam:output/tapi-oam:oam-job" {
        container eth-on-demand-single-ended-measurement-job {
            uses eth-on-demand-single-ended-measurement-job;
            description "none";
        }
        description "none";
    }
    augment "/tapi-oam:update-oam-job/tapi-oam:output/tapi-oam:oam-job" {
        container eth-on-demand-single-ended-measurement-job {
            uses eth-on-demand-single-ended-measurement-job;
            description "none";
        }
        description "none";
    }
    augment "/tapi-oam:update-oam-job/tapi-oam:output/tapi-oam:oam-job" {
        container eth-pro-active-dual-ended-measurement-job {
            uses eth-pro-active-dual-ended-measurement-job;
            description "none";
        }
        description "none";
    }
    augment "/tapi-oam:update-oam-job/tapi-oam:output/tapi-oam:oam-job" {
        container eth-on-demand-dual-ended-measurement-job {
            uses eth-on-demand-dual-ended-measurement-job;
            description "none";
        }
        description "none";
    }
    augment "/tapi-oam:update-oam-job/tapi-oam:output/tapi-oam:oam-job" {
        container eth-pro-active-single-ended-measurement-job {
            uses eth-pro-active-single-ended-measurement-job;
            description "none";
        }
        description "none";
    }
    augment "/tapi-oam:update-oam-job/tapi-oam:output/tapi-oam:oam-job" {
        container eth-test-job {
            uses eth-test-job;
            description "none";
        }
        description "none";
    }
    augment "/tapi-oam:update-oam-job/tapi-oam:input" {
        container eth-on-demand-single-ended-measurement-job {
            uses eth-on-demand-single-ended-measurement-job;
            description "none";
        }
        description "none";
    }
    augment "/tapi-oam:get-oam-job-list/tapi-oam:output/tapi-oam:oam-job" {
        container eth-pro-active-single-ended-measurement-job {
            uses eth-pro-active-single-ended-measurement-job;
            description "none";
        }
        description "none";
    }
    augment "/tapi-oam:get-oam-job-list/tapi-oam:output/tapi-oam:oam-job" {
        container eth-link-trace-job {
            uses eth-link-trace-job;
            description "none";
        }
        description "none";
    }
    augment "/tapi-common:get-service-interface-point-details/tapi-common:output/tapi-common:sip" {
        container eth-service-inteface-point-spec {
            uses eth-service-inteface-point-spec;
            description "none";
        }
        description "none";
    }
    augment "/tapi-connectivity:create-connectivity-service/tapi-connectivity:output/tapi-connectivity:service" {
        container eth-connectivity-service {
            uses eth-connectivity-service;
            description "none";
        }
        description "none";
    }
    augment "/tapi-connectivity:create-connectivity-service/tapi-connectivity:output/tapi-connectivity:service/tapi-connectivity:end-point" {
        container eth-connectivity-service-end-point-spec {
            uses eth-connectivity-service-end-point-spec;
            description "none";
        }
        description "none";
    }
    augment "/tapi-oam:update-oam-service/tapi-oam:output/tapi-oam:oam-service/tapi-oam:oam-service-point" {
        container eth-oam-mep-service-point {
            uses eth-oam-mep-service-point;
            description "none";
        }
        description "none";
    }
    augment "/tapi-oam:get-oam-job/tapi-oam:output/tapi-oam:oam-job" {
        container eth-test-job {
            uses eth-test-job;
            description "none";
        }
        description "none";
    }
    augment "/tapi-oam:create-oam-service/tapi-oam:input/tapi-oam:oam-service-point" {
        container eth-oam-mep-service-point {
            uses eth-oam-mep-service-point;
            description "none";
        }
        description "none";
    }
    augment "/tapi-oam:create-oam-service/tapi-oam:input/tapi-oam:oam-service-point" {
        container eth-oam-mip-service-point {
            uses eth-oam-mip-service-point;
            description "none";
        }
        description "none";
    }
    augment "/tapi-oam:update-oam-service/tapi-oam:input/tapi-oam:oam-service-point" {
        container eth-oam-mep-service-point {
            uses eth-oam-mep-service-point;
            description "none";
        }
        description "none";
    }
    augment "/tapi-oam:update-oam-service/tapi-oam:input/tapi-oam:oam-service-point" {
        container eth-oam-mip-service-point {
            uses eth-oam-mip-service-point;
            description "none";
        }
        description "none";
    }
    /**************************
    * package object-classes
    **************************/ 
    grouping eth-ctp-pac {
        leaf actor-oper-key {
            type uint64;
            config false;
            description "See 802.1AX:
                The current operational value of the Key for the Aggregator. The administrative Key value may differ from the operational Key value for the reasons discussed in 5.6.2.
                The meaning of particular Key values is of local significance.
                range of type : 16 bit";
        }
        leaf actor-system-id {
            type mac-address;
            description "See 802.1AX:
                A MAC address used as a unique identifier for the System that contains this Aggregator.";
        }
        leaf actor-system-priority {
            type uint64;
            description "See 802.1AX:
                Indicating the priority associated with the Actors System ID.
                range of type : 2-octet";
        }
        leaf data-rate {
            type uint64;
            config false;
            description "See 802.1AX:
                The current data rate, in bits per second, of the aggregate link. The value is calculated as N times the data rate of a single link in the aggregation, where N is the number of active links.";
        }
        leaf partner-oper-key {
            type uint64;
            config false;
            description "See 802.1AX:
                The current operational value of the Key for the Aggregators current protocol Partner. If the aggregation is manually configured, this Key value will be a value assigned by the local System.
                range of type : 16-bit";
        }
        leaf partner-system-id {
            type mac-address;
            config false;
            description "See 802.1AX:
                A MAC address consisting of the unique identifier for the current protocol Partner of this Aggregator. A value of zero indicates that there is no known Partner. If the aggregation is manually configured, this System ID value will be a value assigned by the local System.";
        }
        leaf partner-system-priority {
            type uint64;
            config false;
            description "See 802.1AX:
                Indicates the priority associated with the Partners System ID. If the aggregation is manually configured, this System Priority value will be a value assigned by the local System.
                range of type : 2-octet";
        }
        container eth-ctp-common-pac {
            uses eth-ctp-common-pac;
            description "none";
        }
        description "none";
    }
    grouping eth-connection-end-point-spec {
        container ety-term {
            uses ety-termination-pac;
            description "none";
        }
        container eth-term {
            uses eth-termination-pac;
            description "none";
        }
        container eth-ctp {
            uses eth-ctp-pac;
            description "none";
        }
        description "none";
    }
    grouping eth-termination-pac {
        container eth-termination-common-pac {
            uses eth-termination-common-pac;
            description "none";
        }
        description "This object class models the Ethernet Flow Termination function located at a layer boundary.";
    }
    grouping ety-termination-pac {
        container ety-termination-common-pac {
            uses ety-termination-common-pac;
            description "none";
        }
        uses ety-pac;
        description "none";
    }
    grouping traffic-conditioning-pac {
        list prio-config-list {
            key 'queue-id';
            uses priority-configuration;
            description "This attribute indicates the Priority Splitter function for the mapping of the Ethernet frame priority (ETH_CI_P) values to the output queue.";
        }
        list cond-config-list {
            key 'queue-id';
            uses traffic-conditioning-configuration;
            description "This attribute indicates for the conditioner process the conditioning parameters:
                - Queue ID: Indicates the Queue ID
                - Committed Information Rate (CIR): number of bits per second
                - Committed Burst Size (CBS): number of bytes
                - Excess Information Rate (EIR): number of bits per second
                - Excess Burst Size (EBS): number of bytes
                - Coupling flag (CF): 0 or 1
                - Color mode (CM): color-blind and color-aware.";
        }
        leaf codirectional {
            type boolean;
            description "This attribute indicates the direction of the conditioner. The value of true means that the conditioner (modeled as a TCS Sink according to G.8021) is associated with the sink part of the containing CTP. The value of false means that the conditioner (modeled as a TCS Sink according to G.8021) is associated with the source part of the containing CTP.";
        }
        description "This object class models the ETH traffic conditioning function as defined in G.8021.
            Basic attributes: codirectional, condConfigList, prioConfigList";
    }
    grouping traffic-shaping-pac {
        list prio-config-list {
            key 'queue-id';
            uses priority-configuration;
            description "This attribute configures the Priority Splitter function for the mapping of the Ethernet frame priority (ETH_CI_P) values to the output queue.";
        }
        list queue-config-list {
            key 'queue-id';
            uses queue-configuration;
            description "This attribute configures the Queue depth and Dropping threshold parameters of the Queue process. The Queue depth sets the maximum size of the queue in bytes. An incoming ETH_CI traffic unit is dropped if there is insufficient space in the queue to hold the whole unit. The Dropping threshold sets the threshold of the queue. If the queue is filled beyond this threshold, incoming ETH_CI traffic units accompanied by the ETH_CI_DE signal set are dropped.";
        }
        leaf sched-config {
            type scheduling-configuration;
            description "This attribute configures the scheduler process. The value of this attribute is for further study because it is for further study in G.8021.
                Scheduler is a pointer to a Scheduler object, which is to be defined in the future (because in G.8021, this is FFS).
                Note that the only significance of the GTCS function defined in G.8021 is the use of a common scheduler for shaping. Given that, G.8052 models the common scheduler feature by having a common value for this attribute.";
        }
        leaf codirectional {
            type boolean;
            description "This attribute indicates the direction of the shaping function. The value of true means that the shaping (modeled as a TCS Source according to G.8021) is associated with the source part of the containing CTP. The value of false means that the shaping (modeled as a TCS Source according to G.8021) is associated with the sink part of the containing CTP.";
        }
        description "This object class models the ETH traffic shaping function as defined in G.8021.
            Basic attribute: codirectional, prioConfigList, queueConfigList, schedConfig";
    }
    grouping eth-meg-spec {
        container eth-cfm-maintenance-domain {
            uses eth-cfm-maintenance-domain;
            description "none";
        }
        container eth-cfm-maintenance-association {
            uses eth-cfm-maintenance-association;
            description "none";
        }
        container eth-meg-common {
            uses eth-meg-common;
            description "none";
        }
        description "none";
    }
    grouping eth-mep-spec {
        container eth-mep-common {
            uses eth-mep-common;
            description "none";
        }
        container eth-mep-source {
            uses eth-mep-source;
            description "none";
        }
        container eth-mep-sink {
            uses eth-mep-sink;
            description "none";
        }
        leaf mep-mac {
            type mac-address;
            config false;
            description "This attribute contains the MAC Address of the MEP.";
        }
        description "none";
    }
    grouping eth-mip-spec {
        leaf mip-mac {
            type mac-address;
            config false;
            description "This attribute contains the MAC address of the MIP instance.";
        }
        container eth-mip-common {
            uses eth-mip-common;
            description "none";
        }
        description "none";
    }
    grouping eth-loopback-job {
        container eth-oam-test-loopback-common-pac {
            uses eth-oam-test-loopback-common-pac;
            description "none";
        }
        leaf number {
            type uint64;
            description "G.8052: This parameter specifies how many LB messages to be sent for the LB_Series process.";
        }
        leaf lbm-data-tlv {
            type string;
            description "IEEE P802.1Qcx/D0.3:
                String length '1..1480'
                The loopback message Data TLV type.
                MEF 38:
                An arbitrary amount of data to be included in a Data TLV.";
        }
        description "This class represents the Loopback (LB) process (send a series of LB messages carrying a test pattern to a particular MEP). The termination occurs at specified stop time (schedule attribute of OamJob).
            This class models also the 'loopback discover' process, when destinationAddress is multicast.
            When number is greater than 1, then the process is to perform a Loopback (LB) Series process (send a series of N LB messages to a particular MEP/MIP. ";
    }
    grouping eth-mep-common {
        leaf cc-priority {
            type uint64 {
                range "0..7";
            }
            default "7";
            description "This attribute models the MI_CC_Pri signal defined in G.8021 and configured as specified in G8051. It is the priority at which the CCM message should be sent.";
        }
        leaf lck-period {
            type oam-period;
            description "This attribute models the MI_LCK_Period signal defined in G.8021 and configured as specified in G8051. It is the frequency at which the LCK messages should be sent.
                range of type : 1s, 1min";
        }
        leaf lck-priority {
            type uint64 {
                range "0..7";
            }
            default "7";
            description "This attribute models the MI_LCK_Pri signal defined in G.8021 and configured as specified in G8051. It is the priority at which the LCK messages should be sent.";
        }
        leaf mep-identifier {
            type uint64;
            description "IEEE P802.1Qcx/D0.3:
                MEF 38:
                Integer that is unique among all the MEPs in the same Maintenance Association (MEG).
                G.8052:
                This attribute contains the identifier of the MEP.";
        }
        leaf codirectional {
            type boolean;
            default "true";
            description "This attribute specifies the directionality of the Ethernet MEP with respect to the associated CEP. The value of TRUE means that the sink part of the MEP terminates the same signal direction as the sink part of the CEP. The Source part behaves similarly. This attribute is meaningful only when CEP is bidirectional.";
        }
        description "Basic attributes: adminState, clientMel, megIdentifier, mepMac
            Continuity Check Process related attributes: ccPeriod, ccPriority, isCcEnabled
            Lock Process related attributes: lckPeriod, lckPriority
            This object class models the MEP functions that are common to MEP Sink and MEP Source.";
    }
    grouping eth-mep-sink {
        leaf ais-priority {
            type uint64 {
                range "0..7";
            }
            default "7";
            description "This attribute models the MI_AIS_Pri signal defined in G.8021 and configured as specified in G8051. It is the priority at which the AIS messages should be sent.";
        }
        leaf ais-period {
            type oam-period;
            description "This attribute models the MI_AIS_Period signal defined in G.8021 and configured as specified in G8051. It is the frequency at which the AIS messages should be sent.
                range of type : 1s, 1min";
        }
        leaf is-csf-reported {
            type boolean;
            default "true";
            description "This attribute models the MI_CSF_Reported signal defined in G.8021 and configured as specified in G8051. It configures whether the secondary failure CSF should be reported or not.";
        }
        leaf is-csf-rdi-fdi-enabled {
            type boolean;
            default "true";
            description "This attribute models the MI_CSFrdifdiEnable signal defined in G.8021 and configured as specified in G8051.
                aSSFrdi  dCSF-RDI and MI_CSFrdifdiEnable
                aSSFfdi  dCSF-FDI and MI_CSFrdifdiEnable";
        }
        container bandwidth-report {
            config false;
            uses bandwidth-report;
            description "This attribute models the content of the bandwidth report received by the MEP Sink from the peer MEP Source.";
        }
        leaf lm-degm {
            type uint64;
            default "10";
            description "This attribute defines the number of consecutive bad seconds necessary for the 'degraded' detection. See also section 'Degraded signal defect (dDEG)' in G.8021.";
        }
        leaf lm-deg-thr {
            type uint64;
            default "30";
            description "This attribute defines the threshold for declaring a 'bad second'. See also section 'Degraded signal defect (dDEG)' in G.8021.";
        }
        leaf lm-m {
            type uint64 {
                range "2..10";
            }
            default "10";
            description "This attribute defines the number of consecutive good seconds necessary for the clearing of 'degraded'. See also section 'Degraded signal defect (dDEG)' in G.8021.";
        }
        leaf lm-tf-min {
            type uint64;
            description "This attribute defines the necessary number of transmitted frames to enable the detection of 'bad seconds'. See also section 'Degraded signal defect (dDEG)' in G.8021.";
        }
        leaf-list peer-mep-identifier {
            type uint64;
            description "G.8052:
                This attribute models the MI_PeerMEP_ID[i] signal defined in G.8021 and configured as specified in G.8051. It provides the identifiers of the MEPs which are peer to the subject MEP.";
        }
        leaf unexpected-ltr-received {
            type uint64;
            description "IEEE P802.1Qcx/D0.3:
                MEF 38:
                The total number of unexpected LTRs received.";
        }
        description "1DM related attribute: 1DmPriority
            AIS Process related attributes: aisPeriod, aisPriority
            Bandwidth notification Process related attribute: bandwidthReport
            Basic attribute: peerMepRefList
            CSF Process related attributes: isCsfRdiFdiEnabled, isCsfReported
            Defect correlation Process related attribute: currentProblemList
            This object class models the MEP sink function. Instance of this object class can be created and contained by ETH CTP or TTP objects.
            It also provides the management of the dual-ended maintenance job, such as test.
            This object contains the configuration parameters for detecting 'degraded signal' (DEG).";
    }
    grouping eth-mep-source {
        leaf aps-priority {
            type uint64 {
                range "0..7";
            }
            default "7";
            description "This attribute specifies the priority of the APS messages.
                See section 8.1.5    APS insert process in G.8021.";
        }
        leaf csf-priority {
            type uint64 {
                range "0..7";
            }
            default "7";
            description "This attribute models the MI_CSF_Pri signal defined in G.8021 and configured as specified in G8051. It is the priority at which the CSF messages should be sent";
        }
        leaf csf-period {
            type oam-period;
            description "This attribute models the MI_CSF_Period signal defined in G.8021 and configured as specified in G8051. It is the period at which the CSF messages should be sent.
                range of type : 1s, 1min";
        }
        leaf csf-config {
            type csf-config;
            description "This attribute models the combination of all CSF related MI signals (MI_CSF_Enable, MI_CSFrdifdi_Enable, MI_CSFdci_Enable) as defined in G.8021.";
        }
        description "APS Process related attribute: apsPriority
            Basic attribute: mepIdentifier
            CSF Process related attributes: csfConfig, csfPeriod, csfPriority
            Link trace related operation: linkTrace
            Loopback related operations: loopbackDiscover, loopbackSeries, loopbackTest, loopbackTestTerminate
            On demand measurement job control related operation: establishOnDemandDualEndedMeasurementJobSource
            Proactive measurement job control related operation: establishProActiveDualEndedMeasurementJobSource
            Test related operations: testInitiatorStart, testInitiatorTerminate
            This object class models the MEP source function. Instance of this object class can be created and contained by ETH CTP or TTP objects.
            It also provides the management of single-ended maintenance jobs, such as loopback test, loopback discover, loopback series, link trace, and dual-ended maintenance job, such as test.";
    }
    grouping eth-link-trace-job {
        leaf priority {
            type uint64;
            default "7";
            description "G.8052: This parameter provides the priority to be used in the LBM frame.
                G.8052: This parameter provides the priority to be used in the TST frame.";
        }
        leaf destination-address {
            type mac-address;
            description "G.8052: This parameter provides the destination address, i.e., the MAC Address of the target MEP or MIP.";
        }
        leaf time-to-live {
            type uint64;
            description "G.8052: This parameter provides the Time To Live (TTL) parameter of the Link Track protocol.
                The TTL parameter allows the receiver (MIP or MEP) of the LTM frame to determine if the frame can be terminated. TTL is decremented every time the LTM frame is relayed. LTM frame with TTL<=1 is terminated and not relayed.
                IEEE P802.1Qcx/D0.3:
                MEF 38:
                An initial value for the LTM TTL field.";
        }
        container eth-cfm-link-trace-pac {
            uses eth-cfm-link-trace-pac;
            description "none";
        }
        description "This class represents the Link Trace (LT) process for fault localization or for discovering the intermediate MIPs along the link from the MEP Source to a target MEP or MIP. An LTM frame will be sent from the MEP source to the target MEP/MIP.
            The termination occurs at specified stop time (schedule attribute of OamJob).";
    }
    grouping eth-test-job {
        container eth-oam-test-loopback-common-pac {
            uses eth-oam-test-loopback-common-pac;
            description "none";
        }
        leaf test-pattern {
            type test-pattern;
            description "G.8052: This parameter provides the test pattern to be used in the optional Data TLV.
                Examples of test patterns include pseudo-random bit sequence (PRBS) 2^31-1 as specified in clause 5.8 of [ITU-T O.150], all '0' pattern, etc.";
        }
        leaf destination-address {
            type mac-address;
            description "G.8052: This parameter provides the destination address, i.e., the MAC Address of the target MEP or MIP.";
        }
        container eth-test-job-sink-point {
            uses eth-test-job-sink-point;
            description "none";
        }
        leaf number {
            type uint64;
            description "This parameter specifies how many TST messages to be sent.";
        }
        description "This class represents the 1-way on-demand in-service or out-of-service diagnostic test. The diagnostic test includes verifying bandwidth throughput, frame loss, bit errors, etc. TST frames are transmitted.
            The termination occurs at specified stop time (schedule attribute of OamJob).";
    }
    grouping eth-on-demand-measurement-job-control-sink {
        leaf sink-mep-id {
            type uint64;
            description "none";
        }
        leaf source-address {
            type mac-address;
            description "This attribute contains the MAC address of the peer MEP. See G.8013 for details.";
        }
        uses eth-measurement-job-control-common;
        description "This object class represents an on-demand measurement job controller sink for 1-way measurements. It is created as a result of an establishOnDemandDualEndedMeasurementJobSink() operation. It is deleted either automatically after the measurement job has completed (stop time reached) and the performance data AVC notification has been sent, or by an explicit abortOnDemandMeasurementJob() operation when the measurement job is running.";
    }
    grouping eth-on-demand-measurement-job-control-source {
        leaf controller-mep-id {
            type uint64;
            description "none";
        }
        leaf oam-pdu-generation-type {
            type oam-pdu-generation-type;
            description "This attribute contains the pattern that is used for the generation of OAM PDUs.";
        }
        leaf destination-address {
            type mac-address;
            description "This attribute contains the MAC address of the peer MEP. See G.8013 for details.";
        }
        leaf data-tlv-length {
            type uint64;
            description "This parameter provides the size of the optional data TLV.
                Non-negative integer represents the number of bytes for the length of the padding TLV.
                Notes:
                When configuring this parameter one should be aware of the maximum allowed total frame size limitation.
                The attribute is not used in case of 2-way loss measurement.
                range of type : Depends on the allowed MTU size.";
        }
        uses eth-measurement-job-control-common;
        description "Basic attributes: destinationAddress, priority
            Measurement configuration related attributes: oamPduGenerationType, startTime, stopTime, messagePeriod, repetitionPeriod, measurementInterval
            Optional attributes: dataTlvLength, testIdentifier
            This object class represents an on-demand measurement job controller source for 1-way measurements. It is created as a result of an establishOnDemandDualEndedMeasurementJobSource() operation. It is deleted either automatically after the measurement job has completed (stop time reached), or by an explicit abortOnDemandMeasurementJob() operation while the measurement job is running.";
    }
    grouping eth-pro-active-measurement-job-control-sink {
        leaf sink-mep-id {
            type uint64;
            description "none";
        }
        leaf source-address {
            type mac-address;
            description "This attribute contains the MAC address of the peer MEP. See G.8013 for details.";
        }
        leaf is-enabled {
            type boolean;
            default "true";
            description "This attribute identifies the state of the measurement job. If set to TRUE, the MEP performs proactive Performance Measurement.";
        }
        uses eth-measurement-job-control-common;
        description "This object class allows the control of the proactive 1-way measurement. It is created as a part of an establishProActiveDualEndedMeasurementJobSink() operation. Lifecycle: A pre-condition of deleting the object is that the Enable attribute should have the value FALSE.";
    }
    grouping eth-pro-active-measurement-job-control-source {
        leaf controller-mep-id {
            type uint64;
            description "none";
        }
        leaf destination-address {
            type mac-address;
            description "This attribute provides the Unicast MAC address of the intented destination.";
        }
        leaf data-tlv-length {
            type uint64;
            description "This parameter provides the size of the optional data TLV.
                Non-negative integer represents the number of bytes for the length of the padding TLV.
                Notes:
                When configuring this parameter one should be aware of the maximum allowed total frame size limitation.
                The attribute is not used in case of 2-way loss measurement.
                range of type : Depends on the allowed MTU size.";
        }
        leaf is-enabled {
            type boolean;
            default "true";
            description "This attribute identifies the state of the measurement job. If set to TRUE, the MEP performs proactive Performance Measurement.";
        }
        uses eth-measurement-job-control-common;
        description "This object class represents a proactive measurement job controller source for 1way measurements. It is created as a part of an establishProactiveDualEndedMeasurementJobSource() operation.";
    }
    grouping eth-pro-active-1-dm-performance-data {
        container statistical-near-end-1-dm-parameters {
            uses statistical-dm-performance-parameters;
            description "This attribute contains the statistical near end performnace parameters.";
        }
        description "This object class represents the PM current data collected in a pro-active delay measurement job (using 1DM).";
    }
    grouping eth-pro-active-1-lm-performance-data {
        container statistical-near-end-1-lm-parameters {
            uses statistical-lm-performance-parameters;
            description "This attribute contains the statistical near end performnace parameters.";
        }
        container total-counters-near-end-1-lm-parameters {
            uses total-counters-lm-performance-parameters;
            description "This attribute contains the results of an on-demand synthetic loss measurement job in the ingress direction.";
        }
        description "This object class represents the PM current data collected in a pro-active loss measurement job (using 1SL).";
    }
    grouping eth-pro-active-dm-performance-data {
        container statistical-bi-dir-dm-parameters {
            uses statistical-dm-performance-parameters;
            description "This attribute contains the statistical bidirectional performnace parameters.";
        }
        container statistical-far-end-dm-parameters {
            uses statistical-dm-performance-parameters;
            description "This attribute contains the statistical far end performnace parameters.";
        }
        container statistical-near-end-dm-parameters {
            uses statistical-dm-performance-parameters;
            description "This attribute contains the statistical near end performnace parameters.";
        }
        description "This object class represents the PM current data collected in a pro-active delay measurement job (using DMM/DMR).";
    }
    grouping eth-pro-active-lm-performance-data {
        container statistical-far-end-lm-parameters {
            uses statistical-lm-performance-parameters;
            description "This attribute contains the statistical far end performnace parameters.";
        }
        container statistical-near-end-lm-parameters {
            uses statistical-lm-performance-parameters;
            description "This attribute contains the statistical near end performnace parameters.";
        }
        container total-counters-far-end-lm-parameters {
            uses total-counters-lm-performance-parameters;
            description "This attribute contains the results of an on-demand synthetic loss measurement job in the egress direction.";
        }
        container total-counters-near-end-lm-parameters {
            uses total-counters-lm-performance-parameters;
            description "This attribute contains the results of an on-demand synthetic loss measurement job in the ingress direction.";
        }
        leaf bidir-unavailable-intervals {
            type uint64;
            description "A generalized (bidirectional) UAS.
                MEF 35.1: A 32-bit counter reflecting the number of delta-t intervals evaluated as Unavailable (i.e., for which A<Controller, Responder>(delta-t) = 0).
                ";
        }
        description "This object class represents the PM current data collected in a pro-active loss measurement job (using LMM/LMR or SLM/SLR).";
    }
    grouping eth-on-demand-1-dm-performance-data {
        container statistical-near-end-1-dm-parameters {
            uses statistical-dm-performance-parameters;
            description "This attribute contains the statistical near end performnace parameters.";
        }
        container samples-near-end-1-dm-parameters {
            uses samples-dm-performance-parameters;
            description "This attribute contains the results of an on-demand frame delay measurement job in the ingress direction.";
        }
        description "none";
    }
    grouping eth-on-demand-1-lm-performance-data {
        container statistical-near-end-1-lm-parameters {
            uses statistical-lm-performance-parameters;
            description "This attribute contains the statistical near end performnace parameters.";
        }
        container total-counters-near-end-1-lm-parameters {
            uses total-counters-lm-performance-parameters;
            description "This attribute contains the results of an on-demand synthetic loss measurement job in the ingress direction.";
        }
        description "none";
    }
    grouping eth-on-demand-dm-performance-data {
        container statistical-bi-dir-dm-parameters {
            uses statistical-dm-performance-parameters;
            description "This attribute contains the statistical bidirectional performnace parameters.";
        }
        container statistical-near-end-dm-parameters {
            uses statistical-dm-performance-parameters;
            description "This attribute contains the statistical near end performnace parameters.";
        }
        container statistical-far-end-dm-parameters {
            uses statistical-dm-performance-parameters;
            description "This attribute contains the statistical far end performnace parameters.";
        }
        container samples-near-end-dm-parameters {
            uses samples-dm-performance-parameters;
            description "This attribute contains the results of an on-demand frame delay measurement job in the ingress direction.";
        }
        container samples-far-end-dm-parameters {
            uses samples-dm-performance-parameters;
            description "This attribute contains the results of an on-demand frame delay measurement job in the ingress direction.";
        }
        description "none";
    }
    grouping eth-on-demand-lm-performance-data {
        container statistical-near-end-lm-parameters {
            uses statistical-lm-performance-parameters;
            description "This attribute contains the statistical near end performnace parameters.";
        }
        container statistical-far-end-lm-parameters {
            uses statistical-lm-performance-parameters;
            description "This attribute contains the statistical far end performnace parameters.";
        }
        container total-counters-near-end-lm-parameters {
            uses total-counters-lm-performance-parameters;
            description "This attribute contains the results of an on-demand synthetic loss measurement job in the ingress direction.";
        }
        container total-counters-far-end-lm-parameters {
            uses total-counters-lm-performance-parameters;
            description "This attribute contains the results of an on-demand synthetic loss measurement job in the egress direction.";
        }
        leaf bidir-unavailable-intervals {
            type uint64;
            description "A generalized (bidirectional) UAS.
                MEF 35.1: A 32-bit counter reflecting the number of delta-t intervals evaluated as Unavailable (i.e., for which A<Controller, Responder>(delta-t) = 0).
                ";
        }
        description "none";
    }
    grouping eth-pro-active-dual-ended-measurement-job {
        container eth-pro-active-measurement-job-control-source {
            uses eth-pro-active-measurement-job-control-source;
            description "none";
        }
        container eth-pro-active-measurement-job-control-sink {
            uses eth-pro-active-measurement-job-control-sink;
            description "none";
        }
        description "none";
    }
    grouping eth-pro-active-single-ended-measurement-job {
        container eth-pro-active-measurement-job-control-source {
            uses eth-pro-active-measurement-job-control-source;
            description "none";
        }
        description "none";
    }
    grouping eth-on-demand-single-ended-measurement-job {
        container eth-on-demand-measurement-job-control-source {
            uses eth-on-demand-measurement-job-control-source;
            description "none";
        }
        description "none";
    }
    grouping eth-on-demand-dual-ended-measurement-job {
        container eth-on-demand-measurement-job-control-source {
            uses eth-on-demand-measurement-job-control-source;
            description "none";
        }
        container eth-on-demand-measurement-job-control-sink {
            uses eth-on-demand-measurement-job-control-sink;
            description "none";
        }
        description "none";
    }
    grouping eth-loopback-result-data {
        leaf rec-lbr-frames {
            type uint64;
            config false;
            description "G.8052: This parameter returns the total number of received LBR messages, including the out of order LBR frames.";
        }
        leaf out-of-order-lbr-frames {
            type uint64;
            config false;
            description "G.8052: This parameter returns the number of LBR traffic unites (messages) that were received out of order (OO).";
        }
        leaf sent-lbm-frames {
            type uint64;
            config false;
            description "G.8052: This parameter returns the total number of sent LBM frames.";
        }
        leaf crc-lbr-frames {
            type uint64;
            config false;
            description "G.8052: This parameter returns the number of LBR frames where the CRC in the pattern failed.";
        }
        leaf ber-lbr-frames {
            type uint64;
            config false;
            description "G.8052: This parameter returns the number of LBR frames where there was a bit error in the pattern.";
        }
        leaf-list detected-peer-mep {
            type mac-address;
            config false;
            description "G.8052: This parameter returns the MAC addresses of the discovered peer MEPs of the subject MEP.";
        }
        description "none";
    }
    grouping eth-link-trace-result-data {
        list result-list {
            key 'source-address';
            config false;
            uses link-trace-result;
            description "G.8052: This parameter returns the results of the LT process. It contains a list of the result received from the individual LTR frames.
                The result from the individual LTR frame include the Source Mac Address, the TTL, and TLV.";
        }
        list eth-cfm-link-trace-result-data {
            key 'seq-number';
            uses eth-cfm-link-trace-result-data;
            description "none";
        }
        description "none";
    }
    grouping eth-test-result-data {
        leaf sent-tst-frames {
            type uint64;
            config false;
            description "G.8052: This parameter returns the total number of sent TST frames.
                Optional in case of sink only MEP.";
        }
        leaf rec-tst-frames {
            type uint64;
            description "Received TST frames. Optional in case of source only MEP.";
        }
        description "none";
    }
    grouping eth-oam-test-loopback-common-pac {
        leaf period {
            type oam-period;
            description "G.8052: This parameter provides the periodicity of the TST OAM messages.
                G.8052: This parameter provides the periodicity of the LBM OAM messages used in the LB Series process.";
        }
        leaf drop-eligibility {
            type boolean;
            description "G.8052: This parameter provides the eligibility of frames with unicast ETH-TST information to be discarded when congestion conditions are encountered.
                G.8052: This parameter provides the eligibility of frames with unicast ETH-LB information to be discarded when congestion conditions are encountered.";
        }
        leaf data-tlv-length {
            type uint64;
            description "G.8052: This parameter provides the length (in number of octet) of the optional Data TLV to be included in the TST frame.";
        }
        description "none";
    }
    grouping eth-cfm-maintenance-domain {
        leaf maintenance-domain-name-type {
            type maintenance-domain-name-type;
            description "IEEE P802.1Qcx/D0.3:
                MEF 38:
                The Maintenance Domain name format choice.";
        }
        leaf maintenance-domain-name {
            type string;
            description "IEEE P802.1Qcx/D0.3:
                MEF 38:
                A reference to the maintenance domain that this maintenance group is associated with.";
        }
        description "IEEE CFM parameters applicable to the composing class.
            IEEE P802.1Qcx/D0.3:
            MEF 38:
            A Maintenance Domain is the network or the part of the network for which faults in connectivity can be managed.
            A Maintenance Domain object is required in order to create an MA with a Maintenance Association Identifier (MAID) that includes that Maintenance Domains Name.
            From this Maintenance Domain managed object, all Maintenance Association managed objects associated with that Maintenance Domain managed object can be accessed, and thus controlled.";
    }
    grouping eth-cfm-maintenance-association {
        container maintenance-association-name {
            uses maintenance-association-name;
            description "IEEE P802.1Qcx/D0.3:
                MEF 38:
                The Maintenance Association name and name format choice.";
        }
        leaf id-permission {
            type association-id-permission-types;
            description "IEEE P802.1Qcx/D0.3:
                MEF 38:
                This parameter indicates what, if anything, is to be included in the Sender ID TLV transmitted by Maintenance Points configured in this MA.
                A value of 'defer' means that the contents of the Sender ID TLV are determined by the enclosing Maintenance Domain instance.";
        }
        description "IEEE CFM parameters applicable to the composing class.
            IEEE P802.1Qcx/D0.3:
            Provides configuration and operational data for the Maintenance Associations.
            A Maintenance Association is a set of MEPs, each configured with the same MAID and MD level, established to verify the integrity of a single service instance.
            A Maintenance Association can be thought of as a full mesh of Maintenance Entities among a set of MEPs so configured.";
    }
    grouping eth-cfm-link-trace-pac {
        leaf period {
            type oam-period;
            description "IEEE P802.1Qcx/D0.3:
                The interval between LTM transmissions to be used by all MEPs in the Maintenance Association.";
        }
        leaf ltm-flags {
            type ltmflags;
            description "IEEE P802.1Qcx/D0.3:
                MEF 38:
                The flags field for the LTMs transmitted by the MEP.";
        }
        leaf target-mep-id {
            type uint64;
            description "IEEE P802.1Qcx/D0.3:
                MEF 38:
                An indication of a destination MEP, the MEPID of a MEP.
                Alternative to destination MAC address.
                ";
        }
        leaf drop-eligibility {
            type boolean;
            description "IEEE P802.1Qcx/D0.3:
                MEF 38:
                Drop eligible bit value to be used in the VLAN tag, if present in the transmitted frame.";
        }
        description "none";
    }
    grouping eth-cfm-link-trace-result-data {
        leaf seq-number {
            type uint64;
            description "IEEE P802.1Qcx/D0.3:
                type uint32 range '0..4294967295'
                Transaction identifier returned by a previous transmit linktrace message command, indicating which LTMs response is going to be returned.
                MEF 38:
                The LTM Transaction Identifier to which the LTR entries will be attached.";
        }
        leaf receive-order {
            type uint64;
            description "IEEE P802.1Qcx/D0.3:
                MEF 38:
                type uint32 range '1..4294967295'
                An index to distinguish among multiple LTRs with the same LTR Transaction Identifier field value.
                Assigned sequentially from 1, in the order that the Linktrace Initiator received the LTRs.";
        }
        leaf reply-ttl {
            type uint64;
            config false;
            description "IEEE P802.1Qcx/D0.3:
                MEF 38:
                TTL field value for a returned LTR.
                Range '0..255'";
        }
        leaf forwarded {
            type boolean;
            config false;
            description "IEEE P802.1Qcx/D0.3:
                MEF 38:
                Indicates if a LTM was forwarded by the responding MP, as returned in the FwdYes flag of the flags field.";
        }
        leaf terminal-mep {
            type boolean;
            config false;
            description "IEEE P802.1Qcx/D0.3:
                MEF 38:
                A Boolean value stating whether the forwarded LTM reached a MEP enclosing its MA, as returned in the Terminal MEP flag of the Flags field.";
        }
        leaf last-egress-identifier {
            type string;
            config false;
            description "IEEE P802.1Qcx/D0.3:
                MEF 38:
                String length '8'
                An octet field holding the Last Egress Identifier returned in the LTR Egress Identifier TLV of the LTR.
                The Last Egress Identifier identifies the MEP Linktrace Initiator that originated, or the Linktrace Responder that forwarded, the LTM to which this LTR is the response.
                This is the same value as the Egress Identifier TLV of that LTM.";
        }
        leaf next-egress-identifier {
            type string;
            config false;
            description "IEEE P802.1Qcx/D0.3:
                MEF 38:
                String length '8'
                An octet field holding the Next Egress Identifier returned in the LTR Egress Identifier TLV of the LTR.
                The Next Egress Identifier Identifies the Linktrace Responder that transmitted this LTR, and can forward the LTM to the next hop.
                This is the same value as the Egress Identifier TLV of the forwarded LTM, if any.
                If the FwdYes bit of the Flags field is false, the contents of this field are undefined, i.e., any value can be transmitted, and the field is ignored by the receiver.";
        }
        leaf relay-action-field {
            type link-trace-relay-action-field-value;
            config false;
            description "IEEE P802.1Qcx/D0.3:
                MEF 38:
                An enumerated value indicating the value returned in the Relay Action field.
                ";
        }
        leaf ingress-action-field {
            type link-trace-ingress-action-field-value;
            config false;
            description "IEEE P802.1Qcx/D0.3:
                MEF 38:
                The value returned in the Ingress Action Field of the LTM.
                IEEE P802.1Qcx/D0.3:
                The value INGRESS-NO-TLV indicates that no Reply Ingress TLV was returned in the LTM.
                ";
        }
        leaf ingress-mac {
            type mac-address;
            config false;
            description "IEEE P802.1Qcx/D0.3:
                MEF 38:
                MAC address returned in the ingress MAC address field.
                IEEE P802.1Qcx/D0.3:
                If the ingressActionField attribute contains the value INGRESS-NO-TLV, then the contents of this attribute is meaningless.";
        }
        container ingress-port-id {
            config false;
            uses lldp-port-id-subtype;
            description "IEEE P802.1Qcx/D0.3:
                MEF 38:
                Ingress Port ID.
                IEEE P802.1Qcx/D0.3:
                If the ingressActionField attribute contains the value INGRESS-NO-TLV, then the contents of this attribute are meaningless.";
        }
        leaf egress-action-field {
            type link-trace-egress-action-field-value;
            config false;
            description "IEEE P802.1Qcx/D0.3:
                MEF 38:
                An enumerated value indicating the value returned in the Egress Action field.
                IEEE P802.1Qcx/D0.3:
                The value EGRESS-NO-TLV indicates that no Reply Egress TLV was returned in the LTM.";
        }
        leaf egress-mac {
            type mac-address;
            config false;
            description "IEEE P802.1Qcx/D0.3:
                MEF 38:
                MAC address returned in the egress MAC address field.
                IEEE P802.1Qcx/D0.3:
                If the egressActionField contains the value EGRESS-NO-TLV, then the contents of this attribute are meaningless.";
        }
        container egress-port-id {
            config false;
            uses lldp-port-id-subtype;
            description "MEF 38:
                IEEE P802.1Qcx/D0.3:
                Egress Port ID.
                IEEE P802.1Qcx/D0.3:
                If the egressActionField attribute contains the value EGRESS-NO-TLV, then the contents of this attribute are meaningless.";
        }
        leaf organization-specific-tlv {
            type string;
            config false;
            description "String length '0 | 4..1500';
                All Organization specific TLVs returned in the LTR, if any. Includes all octets including and following the TLV Length field of each TLV, concatenated together.";
        }
        container chassis-id {
            config false;
            uses lldp-chassis-id-subtype;
            description "MEF 38:
                The chassis-id-subtype contains the chassis ID entity that is listed in the chassis ID field. This is a combination of the 'Chassis ID Subtype' and 'chsssis ID' fields.
                IEEE P802.1Qcx/D0.3:
                The Chassis ID returned in the Sender ID TLV of the LTR, if any.
                The format of a chassis identifier string. Objects of this type are always used with an associated lldp-chassis-is-subtype object, which identifies the format of the particular lldp-chassis-id object instance.
                If the associated lldp-chassis-id-subtype object has a value of chassis-component, then the octet string identifies a particular instance of the entPhysicalAlias object (defined in IETF RFC 2737) for a chassis component (i.e., an entPhysicalClass value of chassis(3)).
                If the associated lldp-chassis-id-subtype object has a value of interface-alias, then the octet string identifies a particular instance of the ifAlias object (defined in IETF RFC 2863) for an interface on the containing chassis.
                If the particular ifAlias object does not contain any values, another chassis identifier type should be used.";
        }
        description "IEEE P802.1Qcx/D0.3:
            MEF 38:
            An index to distinguish among multiple LTRs with the same LTR  transaction-id field value. 
            Assigned sequentially from 1, in the order that the Linktrace Initiator received the LTRs.
            ";
    }
    grouping eth-oam-service {
        container eth-cfm-maintenance-domain {
            uses eth-cfm-maintenance-domain;
            description "none";
        }
        container eth-cfm-maintenance-association {
            uses eth-cfm-maintenance-association;
            description "none";
        }
        container eth-meg-common {
            uses eth-meg-common;
            description "none";
        }
        description "This class defines the parameters for configuration of MEG.";
    }
    grouping eth-oam-mep-service-point {
        container eth-mep-sink {
            uses eth-mep-sink;
            description "none";
        }
        container eth-mep-source {
            uses eth-mep-source;
            description "none";
        }
        container eth-mep-common {
            uses eth-mep-common;
            description "none";
        }
        description "This class defines the common parameters for configuration of Sink and/or Source MEP.";
    }
    grouping eth-oam-mip-service-point {
        container eth-mip-common {
            uses eth-mip-common;
            description "none";
        }
        description "This class defines the common parameters for configuration of MIP.";
    }
    grouping eth-mip-common {
        leaf is-full-mip {
            type boolean;
            config false;
            description "This attribute indicates whether the MIP is a full MIP (true) or a down-half MIP (false). Up-half MIP is not foreseen by G.8052";
        }
        description "none";
    }
    grouping eth-meg-common {
        leaf meg-level {
            type uint64;
            description "none";
        }
        leaf client-mel {
            type uint64;
            description "none";
        }
        leaf meg-identifier {
            type string;
            description "Optional in case 802.1Q maintenanceAssociationName is used.";
        }
        leaf is-cc-enabled {
            type boolean;
            description "This attribute models the MI_CC_Enable signal defined in G.8021 and configured as specified in G8051.
                ITU-T G.8013/Y.1731 (2015)/Amd.1 (11/2018): When ETH-CC transmission is enabled in a MEG,
                all MEPs are enabled to periodically transmit frames with ETH-CC information to their peer MEPs in the MEG.";
        }
        leaf cc-period {
            type oam-period;
            description "This attribute models the MI_CC_Period signal defined in G.8021 and configured as specified in G8051. 
                It is the period at which the CCM message should be sent. 
                Default values are: 3.33 ms for PS, 100 ms for PM, 1 s for FM.
                ITU-T G.8013/Y.1731 (2015)/Amd.1 (11/2018): The ETH-CC transmission period is the same for all MEPs in the MEG.";
        }
        description "none";
    }
    grouping eth-test-job-sink-point {
        leaf source-address {
            type mac-address;
            description "This attribute contains the MAC address of the peer MEP.";
        }
        description "none";
    }
    grouping eth-measurement-job-control-common {
        leaf priority {
            type uint64 {
                range "0..7";
            }
            default "7";
            description "This attribute contains the priority value on which the MEP performs the measurement.
                When the measurement is enabled, the MEP should use this value to encode the priority of generated measurement frames (OAM PDU frames.).
                The EMF usese this value to assign the P parameter of the measurement operation.";
        }
        leaf test-identifier {
            type uint64;
            description "This attribute is used to distinguish each measurement session if multiple measurement sessions are simultaneously activated towards a peer MEP including concurrent on-demand and proactive tests.
                It must be unique at least within the context of any measurement type for the MEG and initiating MEP.
                Note: The attribute is not used in case of 2-way loss measurement.
                range of type : 0..(2^32) - 1";
        }
        leaf message-period {
            type uint64;
            default "1000";
            description "This attribute indicates the period (frequency) of the measurement frame transmission.
                Note that the value 0 means that only one OAM message per measurement interval is generated.
                Unit is milliseconds.
                range of type : 100ms, 1s, 10s";
        }
        leaf measurement-interval {
            type uint64;
            description "This attribute contains the discrete non overlapping periods of time (in seconds) during which measurements are performed
                (i.e., OAM messages are generated) and reports are gathered at the end of the measurement intervals.
                Note that the value 0 means a degenerated measurement interval with a single OAM message and the report is sent as immediately as possible.";
        }
        leaf repetition-period {
            type repetition-period;
            description "This attribute contains the time between the start of two measurement intervals. This IS applicable for the repetitive instance type and MAY be applicable for the repetitive series type. 
                Note that a value of 0 means not applicable (NA), which is for the cases of single instance, single series, or repetitive series without extra gap in between the measurement intervals (i.e., also as known as continuous series).";
        }
        leaf time-of-the-day-alignment {
            type boolean;
            default "true";
            description "MEF 35.1:
                [D7] A SOAM PM Implementation SHOULD allow for no alignment to the time-of-day clock.";
        }
        leaf offset-from-time-of-the-day {
            type uint64;
            description "MEF 35.1:
                [D8] A SOAM PM Implementation SHOULD support a configurable (in minutes) offset from ToD time for alignment of the start of Measurement Intervals other than the first Measurement Interval.";
        }
        leaf flr-availability-delta-time {
            type uint64;
            default "1";
            description "Time length over which each Availability Frame Loss Ratio value is calculated.
                MEF 35.1:
                [R78]/[CR58] [O8] A SOAM PM Implementation MUST support a configurable parameter for the length of time over which each Availability flr value is calculated, with a range of 1s – 300s.  This parameter is equivalent to delta-t as specified by MEF 10.3.
                [R79]/[CR59] [O8] The length of time over which each Availability flr value is calculated (delta-t) MUST be an integer multiple of the interval between each SLM/1SL frame transmission.
                [D31]/[CD16] [O8] The default length of time over which each Availability flr value is calculated SHOULD be 1s.";
        }
        leaf flr-availability-threshold {
            type decimal64 {
                fraction-digits 7;
            }
            default "0.1";
            description "Frame loss ratio threshold to be used in evaluating the Available/Unavailable state of each time interval (as specified by Availability Delta Time).
                MEF 35.1:
                [R81]/[CR61] A SOAM PM Implementation MUST support a configurable Availability frame loss ratio threshold to be used in evaluating the Available/Unavailable state of each delta-t interval per MEF 10.3
                [R82]/[CR62] The Availability frame loss ratio threshold range of 0.00 through 1.00 MUST be supported in increments of 0.01.
                [D33]/[CD18] [O8] The default Availability frame loss ratio threshold SHOULD be 0.1.";
        }
        leaf flr-availability-samples {
            type uint64;
            default "10";
            description "Number of consecutive Availability Frame Loss Ratio measurements to be used to determine Available/Unavailable state transitions.
                MEF 35.1:
                [R80]/[CR60] [O8] The number range of 1 through 10 MUST be supported for the configurable number of consecutive Availability flr measurements to be used to determine Available/Unavailable state transitions.
                This parameter is equivalent to the Availability parameter of n as specified by MEF 10.3.
                [D32]/[CD17] [O8] The default number of n for Availability SHOULD be 10.";
        }
        description "Time length over which each Availability Frame Loss Ratio value is calculated. This parameter allows to generalize SES and UAS.
            MEF 35.1:
            [R78]/[CR58] [O8] A SOAM PM Implementation MUST support a configurable parameter for the length of time over which each Availability flr value is calculated, with a range of 1s – 300s.  This parameter is equivalent to delta-t as specified by MEF 10.3.
            [R79]/[CR59] [O8] The length of time over which each Availability flr value is calculated (delta-t) MUST be an integer multiple of the interval between each SLM/1SL frame transmission.
            [D31]/[CD16] [O8] The default length of time over which each Availability flr value is calculated SHOULD be 1s.";
    }
    grouping eth-pro-active-1-dm-source-performance-data {
        description "This object class represents the PM current data collected in a pro-active delay measurement job (using 1DM), on the source or controller MEP.";
    }
    grouping eth-pro-active-1-lm-source-performance-data {
        description "This object class represents the PM current data collected in a pro-active loss measurement job (using 1SL), on the source or controller MEP.";
    }
    grouping eth-on-demand-1-lm-source-performance-data {
        description "none";
    }
    grouping eth-on-demand-1-dm-source-performance-data {
        description "none";
    }
    grouping eth-connectivity-service-end-point-spec {
        container ety-termination-common-pac {
            uses ety-termination-common-pac;
            description "none";
        }
        container eth-termination-common-pac {
            uses eth-termination-common-pac;
            description "none";
        }
        container eth-ctp-common-pac {
            uses eth-ctp-common-pac;
            description "none";
        }
        description "none";
    }
    grouping ety-termination-common-pac {
        leaf is-fts-enabled {
            type boolean;
            description "This attribute indicates whether Forced Transmitter Shutdown (FTS) is enabled or not. It models the ETYn_TT_So_MI_FTSEnable information.";
        }
        leaf is-tx-pause-enabled {
            type boolean;
            description "This attribute identifies whether the Transmit Pause process is enabled or not. It models the MI_TxPauseEnable defined in G.8021.";
        }
        description "none";
    }
    grouping eth-termination-common-pac {
        container priority-regenerate {
            uses priority-mapping;
            description "This attribute models the ETHx/ETH-m _A_Sk_MI_P_Regenerate information defined in G.8021.";
        }
        leaf priority-code-point-config {
            type pcp-coding;
            description "This attribute models the ETHx/ETH-m _A_Sk_MI_PCP_Config information defined in G.8021.";
        }
        leaf ether-type {
            type vlan-type;
            description "This attribute models the ETHx/ETH-m _A_Sk_MI_Etype information defined in G.8021.";
        }
        leaf frametype-config {
            type frame-type;
            description "This attribute models the ETHx/ETH-m_A_Sk_MI_Frametype_Config information defined in G.8021.";
        }
        leaf-list filter-config-1 {
            type mac-address;
            description "This attribute models the ETHx/ETH-m_A_Sk_MI_Filter_Config information defined in G.8021.
                It indicates the configured filter action for each of the 33 group MAC addresses for control frames.
                The 33 MAC addresses are:
                01-80-C2-00-00-10, 
                01-80-C2-00-00-00 to 01-80-C2-00-00-0F, and 
                01-80-C2-00-00-20 to 01-80-C2-00-00-2F.
                The filter action is Pass or Block. 
                If the destination address of the incoming ETH_CI_D matches one of the above addresses, the filter process shall perform the corresponding configured filter action. 
                If none of the above addresses match, the ETH_CI_D is passed.
                ";
        }
        leaf port-vid {
            type vid;
            default "1";
            description "This attribute models the ETHx/ETH-m _A_Sk_MI_PVID information defined in G.8021.";
        }
        description "none";
    }
    grouping eth-ctp-common-pac {
        leaf-list auxiliary-function-position-sequence {
            type uint64;
            description "This attribute indicates the positions (i.e., the relative order) of all the MEP, MIP, and TCS objects which are associated with the CTP.";
        }
        leaf collector-max-delay {
            type uint64;
            description "See 802.1AX:
                The value of this attribute defines the maximum delay, in tens of microseconds, that may be imposed by the Frame Collector between receiving a frame from an Aggregator Parser, and either delivering the frame to its MAC Client or discarding the frame (see IEEE 802.1AX clause 5.2.3.1.1).
                range of type : 16-bit";
        }
        leaf csf-config {
            type csf-config;
            description "This attribute models the combination of all CSF related MI signals (MI_CSF_Enable, MI_CSFrdifdi_Enable, MI_CSFdci_Enable) as defined in G.8021.
                range of type : true, false";
        }
        leaf csf-rdi-fdi-enable {
            type boolean;
            description "This attribute models the MI_CSFrdifdiEnable information defined in G.8021.";
        }
        leaf csf-report {
            type boolean;
            description "This attribute models the MI_CSF_Reported information defined in G.8021.
                range of type : true, false";
        }
        container filter-config {
            uses control-frame-filter;
            description "This attribute models the FilterConfig MI defined in section 8.3/G.8021. It indicates the configured filter action for each of the 33 group MAC addresses for control frames. The 33 MAC addresses are:
                - All bridges address: 01-80-C2-00-00-10,
                - Reserved addresses: 01-80-C2-00-00-00 to 01-80-C2-00-00-0F,
                - GARP Application addresses: 01-80-C2-00-00-20 to 01-80-C2-00-00-2F.
                The filter action is Pass or Block. 
                If the destination address of the incoming ETH_CI_D matches one of the above addresses, the filter process shall perform the corresponding configured filter action. 
                If none of the above addresses match, the ETH_CI_D is passed.";
        }
        leaf-list filter-config-snk {
            type mac-address;
            description "This attribute models the FilteConfig MI defined in 8.3/G.8021. It indicates the configured filter action for each of the 33 group MAC addresses for control frames. The 33 MAC addresses are:
                01-80-C2-00-00-10, 
                01-80-C2-00-00-00 to 01-80-C2-00-00-0F, and 
                01-80-C2-00-00-20 to 01-80-C2-00-00-2F.
                The filter action is Pass or Block. 
                If the destination address of the incoming ETH_CI_D matches one of the above addresses, the filter process shall perform the corresponding configured filter action. 
                If none of the above addresses match, the ETH_CI_D is passed.";
        }
        leaf is-ssf-reported {
            type boolean;
            description "This attribute provisions whether the SSF defect should be reported as fault cause or not.
                It models the ETH-LAG_FT_Sk_MI_SSF_Reported defined in G.8021.";
        }
        leaf mac-length {
            type uint64;
            default "2000";
            description "This attribute models the MAC_Lenght MI defined in 8.6/G.8021 for the MAC Length Check process. It indicates the allowed maximum frame length in bytes.
                range of type : 1518, 1522, 2000";
        }
        leaf pll-thr {
            type uint64;
            description "This attribute provisions the threshold for the number of active ports. If the number of active ports is more than zero but less than the provisioned threshold, a cPLL (Partial Link Loss) is raised. See section 9.7.1.2 of G.8021.
                range of type : 0..number of ports";
        }
        leaf vlan-config {
            type uint64;
            description "This attribute models the ETHx/ETH-m_A_So_MI_Vlan_Config information defined in G.8021.
                range of type : -1, 0, 1..4094";
        }
        container traffic-shaping-pac {
            uses traffic-shaping-pac;
            description "none";
        }
        container traffic-conditioning-pac {
            uses traffic-conditioning-pac;
            description "none";
        }
        description "none";
    }
    grouping eth-service-inteface-point-spec {
        uses ety-pac;
        description "none";
    }
    grouping ety-pac {
        leaf phy-type {
            type ety-phy-type;
            config false;
            description "This attribute identifies the PHY type of the ETY trail termination. See IEEE 802.3 clause 30.3.2.1.2.";
        }
        leaf-list phy-type-list {
            type ety-phy-type;
            config false;
            description "This attribute identifies the possible PHY types that could be supported at the ETY trail termination. See IEEE 802.3 clause 30.3.2.1.3.";
        }
        description "none";
    }
    grouping eth-connectivity-service {
        description "none";
    }

    /**************************
    * package type-definitions
    **************************/ 
    identity ETH_OAM_JOB_TYPE {
        base tapi-oam:OAM_JOB_TYPE;
        description "none";
    }
    identity ETH_OAM_JOB_TYPE_ETH_1DM {
        base ETH_OAM_JOB_TYPE;
        description "none";
    }
    identity ETH_OAM_JOB_TYPE_ETH_1SLM {
        base ETH_OAM_JOB_TYPE;
        description "none";
    }
    identity ETH_OAM_JOB_TYPE_ETH_LM_CCM {
        base ETH_OAM_JOB_TYPE;
        description "none";
    }
    identity ETH_OAM_JOB_TYPE_ETH_LM_LMM {
        base ETH_OAM_JOB_TYPE;
        description "none";
    }
    identity ETH_OAM_JOB_TYPE_ETH_SLM {
        base ETH_OAM_JOB_TYPE;
        description "none";
    }
    identity ETH_OAM_JOB_TYPE_ETH_DM {
        base ETH_OAM_JOB_TYPE;
        description "none";
    }
    identity ETH_OAM_JOB_TYPE_ETH_LTC {
        base ETH_OAM_JOB_TYPE;
        description "none";
    }
    identity ETH_OAM_JOB_TYPE_ETH_LBK {
        base ETH_OAM_JOB_TYPE;
        description "none";
    }
    identity ETH_OAM_JOB_TYPE_ETH_TEST {
        base ETH_OAM_JOB_TYPE;
        description "none";
    }
    identity MAINTENANCE_DOMAIN_NAME_TYPE {
        description "none";
    }
    identity MAINTENANCE_DOMAIN_NAME_TYPE_NONE {
        base MAINTENANCE_DOMAIN_NAME_TYPE;
        description "IEEE P802.1Qcx/D0.3:
            No format specified, usually because there is not a Maintenance Domain Name. In this case, a zero length OCTET string for the Domain name field is acceptable.
            MEF 38:
            No format specified.";
    }
    identity MAINTENANCE_DOMAIN_NAME_TYPE_DOMAIN-NAME {
        base MAINTENANCE_DOMAIN_NAME_TYPE;
        description "IEEE P802.1Qcx/D0.3:
            MEF 38:
            Domain Name like string, globally unique text string derived from a DNS name.";
    }
    identity MAINTENANCE_DOMAIN_NAME_TYPE_MAC-ADDR-AND-UINT_ {
        base MAINTENANCE_DOMAIN_NAME_TYPE;
        description "IEEE P802.1Qcx/D0.3:
            MEF 38:
            MAC address + 2-octet (unsigned) integer.";
    }
    identity MAINTENANCE_DOMAIN_NAME_TYPE_STRING {
        base MAINTENANCE_DOMAIN_NAME_TYPE;
        description "IEEE P802.1Qcx/D0.3:
            MEF 38:
            RFC2579 DisplayString, except that the character codes 0-31 (decimal) are not used.
            ";
    }
    identity LINK_TRACE_RELAY_ACTION_FIELD_VALUE {
        description "none";
    }
    identity LINK_TRACE_RELAY_ACTION_FIELD_VALUE_RELAY-HIT {
        base LINK_TRACE_RELAY_ACTION_FIELD_VALUE;
        description "The LTM reached a Maintenance Point whose MAC address matches the target address.";
    }
    identity LINK_TRACE_RELAY_ACTION_FIELD_VALUE_RELAY-FDB {
        base LINK_TRACE_RELAY_ACTION_FIELD_VALUE;
        description "The Egress Port was determined by consulting the Filtering Database.";
    }
    identity LINK_TRACE_RELAY_ACTION_FIELD_VALUE_RELAY-MPDB {
        base LINK_TRACE_RELAY_ACTION_FIELD_VALUE;
        description "The Egress Port was determined by consulting the MIP CCM Database.";
    }
    identity LINK_TRACE_INGRESS_ACTION_FIELD_VALUE {
        description "none";
    }
    identity LINK_TRACE_INGRESS_ACTION_FIELD_VALUE_INGRESS-NO-TLV {
        base LINK_TRACE_INGRESS_ACTION_FIELD_VALUE;
        description "Indicates that no Reply Ingress TLV was returned in the LTM.";
    }
    identity LINK_TRACE_INGRESS_ACTION_FIELD_VALUE_INGRESS-OK {
        base LINK_TRACE_INGRESS_ACTION_FIELD_VALUE;
        description "The target data frame would be passed through to the MAC Relay Entity.";
    }
    identity LINK_TRACE_INGRESS_ACTION_FIELD_VALUE_INGRESS-DOWN {
        base LINK_TRACE_INGRESS_ACTION_FIELD_VALUE;
        description "The Bridge Ports MAC_Operational parameter is false.";
    }
    identity LINK_TRACE_INGRESS_ACTION_FIELD_VALUE_INGRESS-BLOCKED {
        base LINK_TRACE_INGRESS_ACTION_FIELD_VALUE;
        description "The target data frame would not be forwarded if received on this Port due to active topology enforcement.";
    }
    identity LINK_TRACE_INGRESS_ACTION_FIELD_VALUE_INGRESS-VID {
        base LINK_TRACE_INGRESS_ACTION_FIELD_VALUE;
        description "The ingress port is not in the member set of the LTMs VID, and ingress filtering is enabled, so the target data frame would be filtered by ingress filtering.";
    }
    identity LINK_TRACE_EGRESS_ACTION_FIELD_VALUE {
        description "none";
    }
    identity LINK_TRACE_EGRESS_ACTION_FIELD_VALUE_EGRESS-NO-TLV {
        base LINK_TRACE_EGRESS_ACTION_FIELD_VALUE;
        description "Indicates that no Reply Egress TLV was returned in the LTM.";
    }
    identity LINK_TRACE_EGRESS_ACTION_FIELD_VALUE_EGRESS-OK {
        base LINK_TRACE_EGRESS_ACTION_FIELD_VALUE;
        description "The targeted data frame would be forwarded.";
    }
    identity LINK_TRACE_EGRESS_ACTION_FIELD_VALUE_EGRESS-DOWN {
        base LINK_TRACE_EGRESS_ACTION_FIELD_VALUE;
        description "The Egress Port can be identified, but that Bridge Port MAC_Operational parameter is false.";
    }
    identity LINK_TRACE_EGRESS_ACTION_FIELD_VALUE_EGRESS-BLOCKED {
        base LINK_TRACE_EGRESS_ACTION_FIELD_VALUE;
        description "The Egress Port can be identified, but the data frame would not pass through the Egress Port due to active topology management (i.e., the Bridge Port is not in the Forwarding state).";
    }
    identity LINK_TRACE_EGRESS_ACTION_FIELD_VALUE_EGRESS-VID {
        base LINK_TRACE_EGRESS_ACTION_FIELD_VALUE;
        description "The Egress Port can be identified, but the Bridge Port is not in the LTMs VIDs member set, so would be filtered by egress filtering.";
    }
    identity LTMFLAGS {
        description "none";
    }
    identity LTMFLAGS_USE-FDB-ONLY {
        base LTMFLAGS;
        description "IEEE 802.1Q 2018:
            If set, indicates that only MAC addresses learned in a Bridge’s FDB, and not information saved in the MIP CCM Database, is to be used to determine the Egress Port.
            Bit 8 (MSB).";
    }
    identity TEST_PATTERN {
        description "none";
    }
    identity TEST_PATTERN_NULL-SIGNAL-WITHOUT-CRC-32 {
        base TEST_PATTERN;
        description "none";
    }
    identity TEST_PATTERN_NULL-SIGNAL-WITH-CRC-32 {
        base TEST_PATTERN;
        description "none";
    }
    identity TEST_PATTERN_PRBS-2_31-1-WITHOUT-CRC-32 {
        base TEST_PATTERN;
        description "none";
    }
    identity TEST_PATTERN_PRBS-2_31-1-WITH-CRC-32 {
        base TEST_PATTERN;
        description "none";
    }
    identity BANDWIDTH_PROFILE_TYPE {
        description "none";
    }
    identity BANDWIDTH_PROFILE_TYPE_MEF_10.x {
        base BANDWIDTH_PROFILE_TYPE;
        description "none";
    }
    identity BANDWIDTH_PROFILE_TYPE_RFC_2697 {
        base BANDWIDTH_PROFILE_TYPE;
        description "none";
    }
    identity BANDWIDTH_PROFILE_TYPE_RFC_2698 {
        base BANDWIDTH_PROFILE_TYPE;
        description "none";
    }
    identity BANDWIDTH_PROFILE_TYPE_RFC_4115 {
        base BANDWIDTH_PROFILE_TYPE;
        description "none";
    }
    identity ETH_PM_PARAMETER_NAME {
    	base tapi-common:PM_PARAMETER_NAME;
        description "none";
    }
    identity ETH_PM_PARAMETER_NAME_MINIMUM_FRAME_DELAY {
        base ETH_PM_PARAMETER_NAME;
        description "none";
    }
    identity ETH_PM_PARAMETER_NAME_MAXIMUM_FRAME_DELAY {
        base ETH_PM_PARAMETER_NAME;
        description "none";
    }
    identity ETH_PM_PARAMETER_NAME_AVERAGE_FRAME_DELAY {
        base ETH_PM_PARAMETER_NAME;
        description "none";
    }
    identity ETH_PM_PARAMETER_NAME_MINIMUM_FRAME_DELAY_VARIATION {
        base ETH_PM_PARAMETER_NAME;
        description "This attribute contains the minimum frame delay variation measured in units of ns (nano second, 1x10e-9 seconds).
            Y.1563:
            The 2-point frame delay variation (vk) for an Ethernet frame k between SRC and DST is the difference between the absolute Ethernet frame transfer delay (xk) of frame k and a defined reference Ethernet frame transfer delay, d1,2, between those same MPs:  vk = xk – d1,2.";
    }
    identity ETH_PM_PARAMETER_NAME_MAXIMUM_FRAME_DELAY_VARIATION {
        base ETH_PM_PARAMETER_NAME;
        description "This attribute contains the maximum frame delay variation measured in units of ns (nano second, 1x10e-9 seconds).
            Y.1563:
            The 2-point frame delay variation (vk) for an Ethernet frame k between SRC and DST is the difference between the absolute Ethernet frame transfer delay (xk) of frame k and a defined reference Ethernet frame transfer delay, d1,2, between those same MPs:  vk = xk – d1,2.";
    }
    identity ETH_PM_PARAMETER_NAME_AVERAGE_FRAME_DELAY_VARIATION {
        base ETH_PM_PARAMETER_NAME;
        description "This attribute contains the average frame delay variation measured in units of ns (nano second, 1x10e-9 seconds).
            Y.1563:
            The 2-point frame delay variation (vk) for an Ethernet frame k between SRC and DST is the difference between the absolute Ethernet frame transfer delay (xk) of frame k and a defined reference Ethernet frame transfer delay, d1,2, between those same MPs:  vk = xk – d1,2.";
    }
    identity ETH_PM_PARAMETER_NAME_MINIMUM_INTER_FRAME_DELAY_VARIATION {
        base ETH_PM_PARAMETER_NAME;
        description "This attribute contains the minimum frame delay variation measured in units of ns (nano second, 1x10e-9 seconds).
            G.8013/Y.1731:
            Frame delay variation is a measure of the variations in the frame delay between a pair of service frames";
    }
    identity ETH_PM_PARAMETER_NAME_MAXIMUM_INTER_FRAME_DELAY_VARIATION {
        base ETH_PM_PARAMETER_NAME;
        description "This attribute contains the maximum frame delay variation measured in units of ns (nano second, 1x10e-9 seconds).
            G.8013/Y.1731:
            Frame delay variation is a measure of the variations in the frame delay between a pair of service frames";
    }
    identity ETH_PM_PARAMETER_NAME_AVERAGE_INTER_FRAME_DELAY_VARIATION {
        base ETH_PM_PARAMETER_NAME;
        description "This attribute contains the average frame delay variation measured in units of ns (nano second, 1x10e-9 seconds).
            G.8013/Y.1731:
            Frame delay variation is a measure of the variations in the frame delay between a pair of service frames";
    }
    identity ETH_PM_PARAMETER_NAME_MINIMUM_FRAME_LOSS_RATIO {
        base ETH_PM_PARAMETER_NAME;
        description "none";
    }
    identity ETH_PM_PARAMETER_NAME_MAXIMUM_FRAME_LOSS_RATIO {
        base ETH_PM_PARAMETER_NAME;
        description "none";
    }
    identity ETH_PM_PARAMETER_NAME_AVERAGE_FRAME_LOSS_RATIO {
        base ETH_PM_PARAMETER_NAME;
        description "none";
    }
    identity ETH_PM_PARAMETER_NAME_HIGH_LOSS_INTERVALS {
        base ETH_PM_PARAMETER_NAME;
        description "none";
    }
    identity ETH_PM_PARAMETER_NAME_UNAVAILABLE_INTERVALS {
        base ETH_PM_PARAMETER_NAME;
        description "none";
    }
    identity ETH_ALARM_CONDITION_NAME {
        base tapi-fm:ALARM_CONDITION_NAME;
        description "none";
    }
    identity ETH_ALARM_CONDITION_NAME_LOSS_OF_CONTINUITY {
        base ETH_ALARM_CONDITION_NAME;
        description "G.8021: The loss of continuity defect is calculated at the ETH layer. It monitors the presence of continuity in ETH trails.";
    }
    identity ETH_ALARM_CONDITION_NAME_UNEXPECTED_MEL {
        base ETH_ALARM_CONDITION_NAME;
        description "G.8021: Reception of a CCM frame with an invalid MEL value.
            Monitoring of the connectivity in a maintenance entity group.";
    }
    identity ETH_ALARM_CONDITION_NAME_UNEXPECTED_MEP {
        base ETH_ALARM_CONDITION_NAME;
        description "G.8021: Reception of a CCM frame with an invalid MEP value, but with valid MEL and MEG values.
            Monitoring of the connectivity in a maintenance entity group.
            ";
    }
    identity ETH_ALARM_CONDITION_NAME_MISMERGE_UNEXPECTED_MEG {
        base ETH_ALARM_CONDITION_NAME;
        description "G.8021: Reception of a CCM frame with an invalid MEG value, but with a valid MEL value.
            Monitoring of the connectivity in a maintenance entity group.
            ";
    }
    identity ETH_ALARM_CONDITION_NAME_UNEXPECTED_PERIODICITY {
        base ETH_ALARM_CONDITION_NAME;
        description "G.8021: Reception of a CCM frame with an invalid periodicity value, but with valid MEL, MEG and MEP values.
            It detects the configuration of different periodicities at different MEPs belonging to the same MEG.
            ";
    }
    identity ETH_ALARM_CONDITION_NAME_UNEXPECTED_PRIORITY {
        base ETH_ALARM_CONDITION_NAME;
        description "G.8021: Reception of a CCM frame with an invalid priority value, but with valid MEL, MEG, MEP and periodicity values.
            It detects the configuration of different priorities for CCM at different MEPs belonging to the same MEG.
            ";
    }
    identity ETH_ALARM_CONDITION_NAME_LOCKED {
        base ETH_ALARM_CONDITION_NAME;
        description "G.8021: Reception of a LCK frame.";
    }
    identity ETH_ALARM_CONDITION_NAME_AIS {
        base ETH_ALARM_CONDITION_NAME;
        description "G.8021: Reception of an AIS frame.";
    }
    identity ETH_ALARM_CONDITION_NAME_DEGRADED {
        base ETH_ALARM_CONDITION_NAME;
        description "G.8021: The defect is detected if there are MI_LM_DEGM (lmDegm of EthMepSink) consecutive bad seconds and cleared if there are MI_LM_M (lmM of EthMepSink) consecutive good seconds. 
            In order to declare a bad second the number of transmitted frames must exceed a threshold (MI_LM_TFMIN, lmTfMin of EthMepSink).
            Furthermore, if the frame loss ratio (lost frames/transmitted frames) is greater than MI_LM_DEGTHR (lmDegThr of EthMepSink), a bad second is declared.
            This defect is only defined for point-to-point ETH connections. It monitors the connectivity of an ETH trail.
            ";
    }
    identity ETH_ALARM_CONDITION_NAME_RDI {
        base ETH_ALARM_CONDITION_NAME;
        description "G.8021: Remote defect indicator defect, reception by an MEP (indexed by 'i', this index not included in the 'cause' cRDI) of a CCM frame with valid MEL, MEG, MEP and periodicity values and the RDI flag set to x; where x=0 (remote defect clear) and x=1 (remote defect set).";
    }
    identity ETH_ALARM_CONDITION_NAME_CSF {
        base ETH_ALARM_CONDITION_NAME;
        description "G.8021 - ETH layer: Reception of a CSF frame that indicates a client loss of signal (dCSF-LOS) or a client forward defect indication (dCSF-FDI) or a client reverse defect indication (dCSF-RDI).
            The CSF (CSF-LOS, CSF-FDI, and CSF-RDI) defect is calculated at the ETH layer. It monitors the presence of a CSF maintenance signal.
            G.8021 - GFP: dCSF is Client-specific GFP-F and GFP-T (resp. Frame and Transparent) sink processes.
            dCSF-RDI: GFP client signal fail-remote defect indication is raised when a GFP client management frame with the RDI UPI (as defined in Table 6-4 of [ITU-T G.7041]) is received.
            dCSF-RDI is cleared when no such GFP client management frame is received in N x 1000 ms (a value of 3 is suggested for N), a valid GFP client data frame is received, or a GFP client management frame with the DCI UPI is received.
            dCSF-FDI: GFP client signal fail-forward defect indication is raised when a GFP client management frame with the FDI UPI (as defined in Table 6-4 of [ITU-T G.7041]) is received.
            dCSF-FDI is cleared when no such GFP client management frame is received in N x 1000 ms (a value of 3 is suggested for N), a valid GFP client data frame is received, or a GFP client management frame with the DCI UPI is received.
            dCSF-LOS: GFP client signal fail-loss of signal is raised when a GFP client management frame with the LOS UPI (as defined in Table 6-4 of [ITU-T G.7041]) is received.
            dCSF-LOS is cleared when no such GFP client management frame is received in N x 1000 ms (a value of 3 is suggested for N), a valid GFP client data frame is received, or a GFP client management frame with the DCI UPI is received.";
    }
    identity ETH_ALARM_CONDITION_NAME_TOTAL_LINK_LOSS {
        base ETH_ALARM_CONDITION_NAME;
        description "G.8021: LAG - fault cause will be raised if no ports are active for an aggregator.";
    }
    identity ETH_ALARM_CONDITION_NAME_PARTIAL_LINK_LOSS {
        base ETH_ALARM_CONDITION_NAME;
        description "G.8021: LAG - fault cause shall be raised if the number of active ports is less than the provisioned threshold.";
    }
    identity ETH_ALARM_CONDITION_NAME_PLM {
        base ETH_ALARM_CONDITION_NAME;
        description "G.806: The payload label mismatch defect (dPLM) shall be detected if the 'accepted TSL' code does not match the 'expected TSL' code. If the 'accepted TSL' is 'equipped non-specific', the mismatch is not detected (TSL: Trail Signal Label).
            Payload type supervision checks that compatible adaptation functions are used at the source and the sink.
            This is normally done by adding a signal type identifier at the source adaptation function and comparing it with the expected identifier at the sink.
            If they do not match, a payload mismatch is detected.";
    }
    identity ETH_ALARM_CONDITION_NAME_LFD {
        base ETH_ALARM_CONDITION_NAME;
        description "G.806 - Server layer-specific GFP sink processes: GFP loss of frame delineation (dLFD) is raised when the frame delineation process (clause 6.3.1 of [ITU-T G.7041]) is not in the 'SYNC' state.
            dLFD is cleared when the frame delineation process is in the 'SYNC' state.";
    }
    identity ETH_ALARM_CONDITION_NAME_EXM {
        base ETH_ALARM_CONDITION_NAME;
        description "G.806 - Common GFP sink processes: GFP extension header mismatch (dEXM) is raised when the accepted EXI (AcEXI) is different from the expected EXI.
            dEXM is cleared when AcEXI matches the expected EXI or GFP_SF is active.";
    }
    identity ETH_ALARM_CONDITION_NAME_UPM {
        base ETH_ALARM_CONDITION_NAME;
        description "G.806 - Client-specific GFP-F (Frame) and GFP-T (Transparent) sink processes: GFP user payload mismatch (dUPM) is raised when the accepted UPI (AcUPI) is different from the expected UPI.
            dUPM is cleared when AcUPI matches the expected UPI or GFP_SF is active.";
    }
    grouping priority-configuration {
        leaf priority {
            type uint64 {
                range "0..7";
            }
            description "none";
        }
        leaf queue-id {
            type uint64;
            description "none";
        }
        description "none";
    }
    grouping queue-configuration {
        leaf queue-id {
            type uint64;
            description "This attribute indicates the queue id.";
        }
        leaf queue-depth {
            type uint64;
            description "This attribute defines the depth of the queue in bytes.";
        }
        leaf queue-threshold {
            type uint64;
            description "This attribute defines the threshold of the queue in bytes.";
        }
        description "none";
    }
    grouping traffic-conditioning-configuration {
        leaf cir {
            type uint64;
            description "This attribute indicates the Committed Information Rate in bits/s.";
        }
        leaf cbs {
            type uint64;
            description "This attribute indicates the Committed Burst Size in bytes.";
        }
        leaf eir {
            type uint64;
            description "This attribute indicates the Excess Information Rate in bits/s.";
        }
        leaf ebs {
            type uint64;
            description "This attribute indicates the Excess Burst Size in bytes.";
        }
        leaf coupling-flag {
            type boolean;
            description "This attribute indicates the coupling flag.";
        }
        leaf colour-mode {
            type colour-mode;
            description "This attribute indicates the colour mode.";
        }
        leaf queue-id {
            type uint64;
            description "This attribute indicates the queue id.";
        }
        description "none";
    }
    typedef mac-address {
        type string;
        description "This primitive data type contains an Ethernet MAC address defined by IEEE 802a. The format of the address consists of 12 hexadecimal characters, grouped in pairs and separated by '-' (e.g., 03-27-AC-75-3E-1D).";
    }
    grouping priority-mapping {
        leaf priority-0 {
            type uint64 {
                range "0..7";
            }
            description "This attribute defines the new priority value for the old priority value 0.";
        }
        leaf priority-1 {
            type uint64 {
                range "0..7";
            }
            default "1";
            description "This attribute defines the new priority value for the old priority value 1.";
        }
        leaf priority-2 {
            type uint64 {
                range "0..7";
            }
            default "2";
            description "This attribute defines the new priority value for the old priority value 2.";
        }
        leaf priority-3 {
            type uint64 {
                range "0..7";
            }
            default "3";
            description "This attribute defines the new priority value for the old priority value 3.";
        }
        leaf priority-4 {
            type uint64 {
                range "0..7";
            }
            default "4";
            description "This attribute defines the new priority value for the old priority value 4.";
        }
        leaf priority-5 {
            type uint64 {
                range "0..7";
            }
            default "5";
            description "This attribute defines the new priority value for the old priority value 5.";
        }
        leaf priority-6 {
            type uint64 {
                range "0..7";
            }
            default "6";
            description "This attribute defines the new priority value for the old priority value 6.";
        }
        leaf priority-7 {
            type uint64 {
                range "0..7";
            }
            default "7";
            description "This attribute defines the new priority value for the old priority value 7.";
        }
        description "This data type provides the priority mapping done in the 'P Regenerate' process defined in G.8021.";
    }
    typedef vid {
        type string;
        description "This primitive type models the 12 Bit VLAN identifier of a VLAN tag.";
    }
    typedef modify-cross-connection-data {
        type string;
        description "none";
    }
    grouping address-tuple {
        leaf address {
            type mac-address;
            description "This attribute contains the MAC address of the address tuple.";
        }
        leaf-list port-list {
            type mac-address;
            description "This attribute contains the ports associated to the MAC address in the address tuple.";
        }
        description "This data type contains an address tuple consisting of a MAC address and a corresponding port list.";
    }
    typedef scheduling-configuration {
        type string;
        description "The syntax of this dataType is pending on the specification in G.8021, which is for further study.";
    }
    grouping control-frame-filter {
        leaf c-2-00-00-10 {
            type boolean;
            description "This attribute identifies the 'All LANs Bridge Management Group Address'.";
        }
        leaf c-2-00-00-00 {
            type boolean;
            description "This attribute identifies the STP/RSTP/MSTP protocol address.";
        }
        leaf c-2-00-00-01 {
            type boolean;
            description "This attribute identifies the IEEE MAC-specific Control Protocols group address (PAUSE protocol).";
        }
        leaf c-2-00-00-02 {
            type boolean;
            description "This attribute identifies the IEEE 802.3 Slow_Protocols_Multicast address (LACP/LAMP or Link OAM protocols).";
        }
        leaf c-2-00-00-03 {
            type boolean;
            description "This attribute identifies the Nearest non-TPMR Bridge group address (Port Authentication protocol).";
        }
        leaf c-2-00-00-04 {
            type boolean;
            description "This attribute identifies the IEEE MAC-specific Control Protocols group address.";
        }
        leaf c-2-00-00-05 {
            type boolean;
            description "Reserved for future standardization.";
        }
        leaf c-2-00-00-06 {
            type boolean;
            description "Reserved for future standardization.";
        }
        leaf c-2-00-00-07 {
            type boolean;
            description "This attribute identifies the Metro Ethernet Forum E-LMI protocol group address.";
        }
        leaf c-2-00-00-08 {
            type boolean;
            description "This attribute identifies the Provider Bridge Group address.";
        }
        leaf c-2-00-00-09 {
            type boolean;
            description "Reserved for future standardization.";
        }
        leaf c-2-00-00-0-a {
            type boolean;
            description "Reserved for future standardization.";
        }
        leaf c-2-00-00-0-b {
            type boolean;
            description "Reserved for future standardization.";
        }
        leaf c-2-00-00-0-c {
            type boolean;
            description "Reserved for future standardization.";
        }
        leaf c-2-00-00-0-d {
            type boolean;
            description "This attribute identifies the Provider Bridge MVRP address.";
        }
        leaf c-2-00-00-0-e {
            type boolean;
            description "This attribute identifies the Individual LAN Scope group address, Nearest Bridge group address (LLDP protocol).";
        }
        leaf c-2-00-00-0-f {
            type boolean;
            description "Reserved for future standardization.";
        }
        leaf c-2-00-00-20 {
            type boolean;
            description "This attribute identifies the Customer and Provider Bridge MMRP address.";
        }
        leaf c-2-00-00-21 {
            type boolean;
            description "This attribute identifies the Customer Bridge MVRP address.";
        }
        leaf c-2-00-00-22 {
            type boolean;
            description "Reserved for future standardization.";
        }
        leaf c-2-00-00-23 {
            type boolean;
            description "Reserved for future standardization.";
        }
        leaf c-2-00-00-24 {
            type boolean;
            description "Reserved for future standardization.";
        }
        leaf c-2-00-00-25 {
            type boolean;
            description "Reserved for future standardization.";
        }
        leaf c-2-00-00-26 {
            type boolean;
            description "Reserved for future standardization.";
        }
        leaf c-2-00-00-27 {
            type boolean;
            description "Reserved for future standardization.";
        }
        leaf c-2-00-00-28 {
            type boolean;
            description "Reserved for future standardization.";
        }
        leaf c-2-00-00-29 {
            type boolean;
            description "Reserved for future standardization.";
        }
        leaf c-2-00-00-2-a {
            type boolean;
            description "Reserved for future standardization.";
        }
        leaf c-2-00-00-2-b {
            type boolean;
            description "Reserved for future standardization.";
        }
        leaf c-2-00-00-2-c {
            type boolean;
            description "Reserved for future standardization.";
        }
        leaf c-2-00-00-2-d {
            type boolean;
            description "Reserved for future standardization.";
        }
        leaf c-2-00-00-2-e {
            type boolean;
            description "Reserved for future standardization.";
        }
        leaf c-2-00-00-2-f {
            type boolean;
            description "Reserved for future standardization.";
        }
        description "This data type identifies the filter action for each of the 33 group MAC addresses (control frames).
            Value 'false' means block: The frame is discarded by the filter process.
            Value 'true' means pass: The frame is passed unchanged through the filter process.";
    }
    grouping bandwidth-report {
        leaf source-mac-address {
            type mac-address;
            description "The sourceMacAddress is the address from the far end.";
        }
        leaf port-id {
            type uint64;
            description "This attribute returns the far end port identifier.";
        }
        leaf nominal-bandwidth {
            type uint64;
            description "This attribute returns the configured bandwidth";
        }
        leaf current-bandwidth {
            type uint64;
            description "This attribute returns the current bandwidth.";
        }
        description "Data type for the bandwidth report.";
    }
    typedef admin-state {
        type enumeration {
            enum LOCK {
                description "none";
            }
            enum NORMAL {
                description "none";
            }
        }
        description "none";
    }
    typedef colour-mode {
        type enumeration {
            enum COLOUR_BLIND {
                description "none";
            }
            enum COLOUR_AWARE {
                description "none";
            }
        }
        description "none";
    }
    typedef csf-config {
        type enumeration {
            enum DISABLED {
                description "This literal covers the following states of the CSF related MI informations:
                    - MI_CSF_Enable is false
                    - MI_CSFrdifdi_Enable is false
                    - MI_CSFdci_Enable is false.";
            }
            enum ENABLED {
                description "This literal covers the following states of the CSF related MI informations:
                    - MI_CSF_Enable is true
                    - MI_CSFrdifdi_Enable is false
                    - MI_CSFdci_Enable is false.";
            }
            enum ENABLED_WITH_RDI_FDI {
                description "This literal covers the following states of the CSF related MI informations:
                    - MI_CSF_Enable is true
                    - MI_CSFrdifdi_Enable is true
                    - MI_CSFdci_Enable is false.";
            }
            enum ENABLED_WITH_RDI_FDI_DCI {
                description "This literal covers the following states of the CSF related MI informations:
                    - MI_CSF_Enable is true
                    - MI_CSFrdifdi_Enable is true
                    - MI_CSFdci_Enable is true.";
            }
            enum ENABLED_WITH_DCI {
                description "This literal covers the following states of the CSF related MI informations:
                    - MI_CSF_Enable is true
                    - MI_CSFrdifdi_Enable is false
                    - MI_CSFdci_Enable is true.";
            }
        }
        description "none";
    }
    typedef ety-phy-type {
        type enumeration {
            enum OTHER {
                description "none";
            }
            enum UNKNOWN {
                description "none";
            }
            enum NONE {
                description "none";
            }
            enum 2BASE_TL {
                description "none";
            }
            enum 10MBIT_S {
                description "none";
            }
            enum 10PASS_TS {
                description "none";
            }
            enum 100BASE_T4 {
                description "none";
            }
            enum 100BASE_X {
                description "none";
            }
            enum 100BASE_T2 {
                description "none";
            }
            enum 1000BASE_X {
                description "none";
            }
            enum 1000BASE_T {
                description "none";
            }
            enum 10GBASE-X {
                description "none";
            }
            enum 10GBASE_R {
                description "none";
            }
            enum 10GBASE_W {
                description "none";
            }
        }
        description "none";
    }
    typedef frame-type {
        type enumeration {
            enum ADMIT_ONLY_VLAN_TAGGED_FRAMES {
                description "none";
            }
            enum ADMIT_ONLY_UNTAGGED_AND_PRIORITY_TAGGED_FRAMES {
                description "none";
            }
            enum ADMIT_ALL_FRAMES {
                description "none";
            }
        }
        description "none";
    }
    typedef oam-period {
        type enumeration {
            enum 3_33MS {
                description "Default for protection.";
            }
            enum 10MS {
                description "none";
            }
            enum 100MS {
                description "none";
            }
            enum 1S {
                description "none";
            }
            enum 10S {
                description "none";
            }
            enum 1MIN {
                description "none";
            }
            enum 10MIN {
                description "none";
            }
        }
        description "Provides the frequency for the OAM PDU insertion.";
    }
    typedef pcp-coding {
        type enumeration {
            enum 8P0D {
                description "none";
            }
            enum 7P1D {
                description "none";
            }
            enum 6P2D {
                description "none";
            }
            enum 5P3D {
                description "none";
            }
            enum DEI {
                description "This enumeration value means that all priorities should be drop eligible.
                    DEI = Drop Eligibility Indicator";
            }
        }
        description "This enum models the coding of the Priority Code Point as defined in section 'Priority Code Point encoding' of IEEE 802.1Q.";
    }
    typedef vlan-type {
        type enumeration {
            enum C_Tag {
                description "0x8100";
            }
            enum S_Tag {
                description "0x88a8";
            }
            enum I_Tag {
                description "88-e7";
            }
        }
        description "This enumeration contains the Ethertypes defined in IEEE 802.1Q.";
    }
    typedef repetition-period {
        type enumeration {
            enum 1MIN {
                description "none";
            }
            enum 1S {
                description "none";
            }
            enum 10S {
                description "none";
            }
            enum 0 {
                description "none";
            }
        }
        description "This enumeration defines the allowed values for the repetition period in on-demand measurements.
            Note: The value 0 means that the value is not relevant.";
    }
    typedef message-period {
        type enumeration {
            enum 10MS {
                description "none";
            }
            enum 100MS {
                description "none";
            }
            enum 1S {
                description "none";
            }
            enum 10S {
                description "none";
            }
            enum 0 {
                description "none";
            }
        }
        description "This enumeration defines the allowed values for the message period in on-demand measurements.
            Notes:
            The value 10ms is only used in synthetic loss measurements.
            The value 0 means that the value is not relevant.";
    }
    typedef oam-pdu-generation-type {
        type enumeration {
            enum SINGLE_INSTANCE {
                description "none";
            }
            enum REPETITIVE_INSTANCE {
                description "none";
            }
            enum SINGLE_SERIES {
                description "none";
            }
            enum REPETITIVE_SERIES {
                description "none";
            }
        }
        description "This enumeration defines the generation pattern of the on-demand OAM PDUs (messages). ";
    }
    grouping samples-dm-performance-parameters {
        leaf number-of-samples {
            type uint64;
            description "This attribute contains the number of received DM frames (successful samples) used for this frame delay measurement.
                range of type : non-negative";
        }
        leaf-list frame-delay-list {
            type uint64;
            description "This attribute contains the frame delays measured in ns (nano second, 1x10e-9 seconds). The multiplicity is defined by the numberOfSamples attribute.";
        }
        leaf-list frame-delay-variation-list {
            type uint64;
            description "This attribute contains the frame delay variations measured in ns (nano second).  The multiplicity is defined by (numberOfSamples - 1, for numberOfSamples > 0).";
        }
        description "This data type contains the results of an on-demand delay measurement job.";
    }
    grouping total-counters-lm-performance-parameters {
        leaf total-transmitted-frames {
            type uint64;
            description "This attribute contains the total number of frames transmitted.";
        }
        leaf total-lost-frames {
            type uint64;
            description "This attribute contains the total number of frames lost.";
        }
        leaf total-frame-loss-ratio {
            type decimal64 {
                fraction-digits 7;
            }
            description "This attribute contains the frame loss ratio (number of lost frames divided by the number of total frames (N_LF / N_TF)).
                The accuracy of the value is for further study.";
        }
        description "This data type contains the results of an on-demand loss measurement job.";
    }
    grouping statistical-dm-performance-parameters {
        leaf minimum-frame-delay {
            type uint64;
            description "This attribute contains the minimum frame delay observed over the monitored period. It is measured in units of ns (nano second, 1x10e-9 seconds).";
        }
        leaf average-frame-delay {
            type uint64;
            description "This attribute contains the average frame delay observed over the monitored period. It is measured in units of ns (nano second, 1x10e-9 seconds).";
        }
        leaf maximum-frame-delay {
            type uint64;
            description "This attribute contains the maximum frame delay observed over the monitored period. It is measured in units of ns (nano second, 1x10e-9 seconds).";
        }
        leaf minimum-frame-delay-variation {
            type uint64;
            description "This attribute contains the minimum frame delay variation measured in units of ns (nano second, 1x10e-9 seconds).
                Y.1563:
                The 2-point frame delay variation (vk) for an Ethernet frame k between SRC and DST is the difference between the absolute Ethernet frame transfer delay (xk) of frame k and a defined reference Ethernet frame transfer delay, d1,2, between those same MPs:  vk = xk – d1,2.";
        }
        leaf average-frame-delay-variation {
            type uint64;
            description "This attribute contains the average frame delay variation measured in units of ns (nano second, 1x10e-9 seconds).
                Y.1563:
                The 2-point frame delay variation (vk) for an Ethernet frame k between SRC and DST is the difference between the absolute Ethernet frame transfer delay (xk) of frame k and a defined reference Ethernet frame transfer delay, d1,2, between those same MPs:  vk = xk – d1,2.";
        }
        leaf maximum-frame-delay-variation {
            type uint64;
            description "This attribute contains the maximum frame delay variation measured in units of ns (nano second, 1x10e-9 seconds).
                Y.1563:
                The 2-point frame delay variation (vk) for an Ethernet frame k between SRC and DST is the difference between the absolute Ethernet frame transfer delay (xk) of frame k and a defined reference Ethernet frame transfer delay, d1,2, between those same MPs:  vk = xk – d1,2.";
        }
        leaf minimum-inter-frame-delay-variation {
            type uint64;
            description "This attribute contains the minimum frame delay variation measured in units of ns (nano second, 1x10e-9 seconds).
                G.8013/Y.1731:
                Frame delay variation is a measure of the variations in the frame delay between a pair of service frames";
        }
        leaf average-inter-frame-delay-variation {
            type uint64;
            description "This attribute contains the average frame delay variation measured in units of ns (nano second, 1x10e-9 seconds).
                G.8013/Y.1731:
                Frame delay variation is a measure of the variations in the frame delay between a pair of service frames";
        }
        leaf maximum-inter-frame-delay-variation {
            type uint64;
            description "This attribute contains the maximum frame delay variation measured in units of ns (nano second, 1x10e-9 seconds).
                G.8013/Y.1731:
                Frame delay variation is a measure of the variations in the frame delay between a pair of service frames";
        }
        description "This data type contains the statistical delay measurement performance parameters.";
    }
    grouping statistical-lm-performance-parameters {
        leaf minimum-frame-loss-ratio {
            type decimal64 {
                fraction-digits 7;
            }
            description "This attribute contains the minimum frame loss ratio calculated over a period of time.";
        }
        leaf average-frame-loss-ratio {
            type decimal64 {
                fraction-digits 7;
            }
            description "This attribute contains the average frame loss ratio calculated over a period of time.";
        }
        leaf maximum-frame-loss-ratio {
            type decimal64 {
                fraction-digits 7;
            }
            description "This attribute contains the maximum frame loss ratio calculated over a period of time.";
        }
        leaf hli-count {
            type uint64;
            description "A generalized SES.
                MEF 10.3: The Resiliency attributes are similar to the definitions of Severely Errored Seconds (SES) and Consecutive SES in section 9 and Annex B (respectively) of Y.1563 [6], when delta-t = 1 second.
                MEF 35.1: Count of High Loss Intervals during the Measurement Interval.
                range of type : 0..900 for 15min interval or 0..86400 for 24 hr interval.";
        }
        leaf unavailable-intervals {
            type uint64;
            description "A generalized UAS.
                MEF 35.1: A 32-bit counter reflecting the number of delta-t intervals evaluated as Unavailable (i.e., for which A<Controller, Responder>(delta-t) = 0).
                range of type : 0..900 for 15min interval or 0..86400 for 24 hr interval.";
        }
        description "This data type contains the statistical loss measurement performance parameters.";
    }
    typedef eth-oam-job-type {
        type identityref {
            base ETH_OAM_JOB_TYPE;
        }
        description "none";
    }
    grouping link-trace-result {
        leaf source-address {
            type mac-address;
            description "G.8052: This attribute contains the source MAC Address of an individual LTR frame result.";
        }
        leaf time-to-live {
            type uint64;
            description "G.8052: This attribute contains the Time To Live (TTL) value of an individual LTR frame result.";
        }
        leaf data-tlv-length {
            type uint64;
            description "G.8052: This attribute contains the length (in number of octets) of the Data TLV of an individual LTR frame result.";
        }
        description "G.8052: This data type contains the result from an individual LTR frame.";
    }
    typedef maintenance-domain-name-type {
        type identityref {
            base MAINTENANCE_DOMAIN_NAME_TYPE;
        }
        description "IEEE P802.1Qcx/D0.3:
            MEF 38:
            The Maintenance Domain format choice.";
    }
    typedef maintenance-domain-id-permission-types {
        type enumeration {
            enum SEND-ID-NONE {
                description "The Sender ID TLV is not to be sent.";
            }
            enum SEND-ID-CHASSIS {
                description "The Chassis ID Length, Chassis ID Subtype, and Chassis ID fields of te Sender ID TLV are to be sent.";
            }
            enum SEND-ID-MANAGE {
                description "The Management Address Length and Management Address of the Sender ID TLV are to be sent.";
            }
            enum SEND-ID-CHASSIS-MANAGE {
                description "The Chassis ID Length, Chassis ID Subtype, Chassis ID, Management Address Length and Management Address fields are all to be sent.";
            }
        }
        description "IEEE P802.1Qcx/D0.3:
            MEF 38:
            Indicates what, if anything, is to be included in the Sender ID TLV transmitted in CCMs, LBMs, LTMs, and LTRs.";
    }
    typedef association-id-permission-types {
        type enumeration {
            enum SEND-ID-NONE {
                description "The Sender ID TLV is not to be sent.";
            }
            enum SEND-ID-CHASSIS {
                description "The Chassis ID Length, Chassis ID Subtype, and Chassis ID fields of te Sender ID TLV are to be sent.";
            }
            enum SEND-ID-MANAGE {
                description "The Management Address Length and Management Address of the Sender ID TLV are to be sent.";
            }
            enum SEND-ID-CHASSIS-MANAGE {
                description "The Chassis ID Length, Chassis ID Subtype, Chassis ID, Management Address Length and Management Address fields are all to be sent.";
            }
            enum SEND-ID-DEFER {
                description "IEEE P802.1Qcx/D0.3:
                    MEF 38:
                    The content of the Sender ID TLV are determined by the corresponding Maintenance Domain variable.";
            }
        }
        description "IEEE P802.1Qcx/D0.3:
            MEF 38:
            Indicates what, if anything, is to be included in the Sender ID TLV transmitted in CCMs, LBMs, LTMs, and LTRs.";
    }
    grouping maintenance-association-name {
        leaf ieee-reserved {
            type string;
            default "0";
            description "IEEE P802.1Qcx/D0.3:
                Reserved for definition by IEEE 802.1. Recommend not to use zero unless absolutely needed.
                Length '1..45'.";
        }
        leaf primary-vlan-id {
            type vid;
            description "IEEE P802.1Qcx/D0.3:
                MEF 38:
                Primary VLAN ID. 12 bits represented in a 2-octet integer.";
        }
        leaf char-string {
            type string;
            description "IEEE P802.1Qcx/D0.3:
                MEF 38:
                RFC2579 DisplayString, except that the character codes 0-31 (decimal) are not used.
                Length '1..45'";
        }
        leaf unsigned-int-16 {
            type uint64;
            description "IEEE P802.1Qcx/D0.3:
                MEF 38:
                2-octet integer/big endian.";
        }
        leaf rfc-2865-vpn-id {
            type string;
            description "IEEE P802.1Qcx/D0.3:
                MEF 38:
                RFC2685 VPN ID. 3 octet VPN authority Organizationally Unique Identifier followed by 4 octet VPN index identifying VPN according to the OUI.
                Length '1..45';";
        }
        leaf icc-format {
            type string;
            description "IEEE P802.1Qcx/D0.3:
                ICC-based format as specified in ITU-T Y.1731.
                Length '1..45'";
        }
        description "none";
    }
    typedef link-trace-relay-action-field-value {
        type identityref {
            base LINK_TRACE_RELAY_ACTION_FIELD_VALUE;
        }
        description "IEEE P802.1Qcx/D0.3:
            MEF 38:
            Possible values the Relay action field can take.";
    }
    typedef link-trace-ingress-action-field-value {
        type identityref {
            base LINK_TRACE_INGRESS_ACTION_FIELD_VALUE;
        }
        description "IEEE P802.1Qcx/D0.3:
            MEF 38:
            Possible values returned in the ingress action field.";
    }
    grouping lldp-port-id-subtype {
        leaf interface-alias {
            type string;
            description "String length '0..64'
                Represents a port identifier based on the ifAlias MIB object, defined in IETF RFC 2863.";
        }
        leaf port-component {
            type string;
            description "String length '0..32'
                Represents a port identifier based on the value of entPhysicalAlias (defined in IETF RFC 2737) for a port component (i.e., entPhysicalClass value of port(10)), within the containing chassis.";
        }
        leaf mac-address {
            type mac-address;
            description "Represents a port identifier based on a unicast source address (encoded in network byte order and IEEE 802.3 canonical bit order), which has been detected by the agent and associated with a particular port (IEEE Std 802-2001).";
        }
        leaf network-address {
            type string;
            description "Represents a port identifier based on a network address, detected by the agent and associated with a particular port.
                Octet string that identifies a particular network address family and an associated network address that are encoded in network octet order.
                An IP address, for example, would be encoded with the first octet containing the IANA Address Family Numbers enumeration value for the specific address type and octets 2 through n containing the address value.
                ";
        }
        leaf interface-name {
            type string;
            description "String length '0..64'
                Represents a port identifier based on the ifName MIB object, defined in IETF RFC 2863.";
        }
        leaf agent-circuit-id {
            type string;
            description "Represents a port identifier based on the agent-local identifier of the circuit (defined in RFC 3046), detected by the agent and associated with a particular port.";
        }
        leaf local {
            type string;
            description "Represents a port identifier based on a value locally assigned.";
        }
        description "IEEE P802.1Qcx/D0.3:
            The source of a particular type of port identifier used in the LLDP YANG module.
            MEF 38:
            Data definitions associated with the Port ID TLV.";
    }
    typedef link-trace-egress-action-field-value {
        type identityref {
            base LINK_TRACE_EGRESS_ACTION_FIELD_VALUE;
        }
        description "IEEE P802.1Qcx/D0.3:
            MEF 38:
            Possible values returned in the Egress Action field.";
    }
    grouping lldp-chassis-id-subtype {
        leaf chassis-component {
            type string;
            description "String length '0..32'
                Represents a chassis identifier based on the value of entPhysicalAlias object (defined in IETF RFC 2737) for a chassis component (i.e., an entPhysicalClass value of chassis(3)).";
        }
        leaf interface-alias {
            type string;
            description "String length '0..64'
                Represents a chassis identifier based on the value of ifAlias object (defined in IETF RFC 2863) for an interface on the containing chassis.";
        }
        leaf port-component {
            type string;
            description "String length '0..32'
                Represents a chassis identifier based on the value of entPhysicalAlias object (defined in IETF RFC 2737) for a port or backplane component (i.e., entPhysicalClass value of port(10) or backplane(4)), within the containing chassis.";
        }
        leaf mac-address {
            type mac-address;
            description "Represents a chassis identifier based on the value of a unicast source address (encoded in network byte order and IEEE 802.3 canonical bit order), of a port on the containing chassis as defined in IEEE Std 802-2001.";
        }
        leaf network-address {
            type string;
            description "Octet string that identifies a particular network address family and an associated network address that are encoded in network octet order.
                An IP address, for example, would be encoded with the first octet containing the IANA Address Family Numbers enumeration value for the specific address type and octets 2 through n containing the address value.";
        }
        leaf interface-name {
            type string;
            description "Represents a chassis identifier based on the value of ifName object (defined in IETF RFC 2863) for an interface on the containing chassis.";
        }
        leaf local {
            type string;
            description "Represents a chassis identifier based on a locally defined value.";
        }
        description "MEF 38:
            The chassis-id-subtype contains the chassis ID entity that is listed in the chassis ID field. This is a combination of the 'Chassis ID Subtype' and 'chassis ID' fields.
            ";
    }
    typedef ltmflags {
        type identityref {
            base LTMFLAGS;
        }
        description "IEEE 802.1Q 2018:
            In the LTM, the Flags field of the Common CFM Header specifies certain options.";
    }
    typedef test-pattern {
        type identityref {
            base TEST_PATTERN;
        }
        description "The following values of pattern types are defined:
            'Null signal without CRC-32'
            'Null signal with CRC-32'
            'PRBS 2^31-1 without CRC-32'
            'PRBS 2^31-1 with CRC-32'.";
    }
    typedef bandwidth-profile-type {
        type identityref {
            base BANDWIDTH_PROFILE_TYPE;
        }
        description "none";
    }
    grouping bandwidth-profile {
        leaf bw-profile-type {
            type bandwidth-profile-type;
            description "none";
        }
        container committed-information-rate {
            uses tapi-common:capacity-value;
            description "none";
        }
        container committed-burst-size {
            uses tapi-common:capacity-value;
            description "none";
        }
        container peak-information-rate {
            uses tapi-common:capacity-value;
            description "none";
        }
        container peak-burst-size {
            uses tapi-common:capacity-value;
            description "none";
        }
        leaf color-aware {
            type boolean;
            description "none";
        }
        leaf coupling-flag {
            type boolean;
            description "none";
        }
        description "none";
    }
    typedef eth-pm-parameter-name {
        type identityref {
            base ETH_PM_PARAMETER_NAME;
        }
        description "none";
    }
    typedef eth-alarm-condition-name {
        type identityref {
            base ETH_ALARM_CONDITION_NAME;
        }
        description "none";
    }

}
