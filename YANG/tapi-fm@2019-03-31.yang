module tapi-fm {
    namespace "urn:onf:otcc:yang:tapi-fm";
    prefix tapi-fm;
    import tapi-common {
        prefix tapi-common;
    }
    import tapi-notification {
        prefix tapi-notification;
    }
    organization "ONF OTCC (Open Transport Configuration & Control) Project";
    contact "
         Project Web: <https://wiki.opennetworking.org/display/OTCC/TAPI>
         Project List: <mailto:transport-api@opennetworking.org>
         Editor: Karthik Sethuraman
                 <mailto:karthik.sethuraman@necam.com>";
    description "
        This module contains TAPI Fault Management Model definitions.
        Source: TapiFm.uml
        Copyright (c) 2018 Open Networking Foundation (ONF). All rights reserved.
        License: This module is distributed under the Apache License 2.0
        - The TAPI YANG models included in this TAPI release are a *normative* part of the TAPI SDK.
        - The YANG specifications have been generated from the corresponding UML model using the [ONF EAGLE UML2YANG mapping tool]
        <https://github.com/OpenNetworkingFoundation/EagleUmlYang>
        and further edited manually to comply with the [ONF IISOMI UML2YANG mapping guidelines]
        <https://wiki.opennetworking.org/display/OIMT/UML+-+YANG+Guidelines>
        - Status of YANG model artifacts can be determined by referring to the corresponding UML artifacts.
        As described in the UML models, some artifacts are considered *experimental*, and thus the corresponding YANG artifacts.
        - The ONF TAPI release process does not guarantee backward compatibility of YANG models across major versions of TAPI releases.
        The YANG model backward compatibility criteria are outlined in section 11 of <https://tools.ietf.org/html/rfc7950>.
        YANG models included in this release may not be backward compatible with previous TAPI releases.";
    revision 2019-03-31 {
        description "ONF Transport API version 2.2-RC1.
                   Changes included in this TAPI release (v2.2) are listed in
                  <https://github.com/OpenNetworkingFoundation/TAPI/blob/develop/CHANGE_LOG/change-log.2.2.md>";
        reference "ONF-TR-527, ONF-TR-512, ONF-TR-531, RFC 7950, RFC 6087 and ONF TAPI UML model
                  <https://github.com/OpenNetworkingFoundation/TAPI/tree/v2.2.0/UML>";
    }
    revision 2018-12-10 {
        description "ONF Transport API version 2.1.1.
                   Changes included in this TAPI release (v2.1.1) are listed in
                  <https://github.com/OpenNetworkingFoundation/TAPI/blob/develop/CHANGE_LOG/change-log.2.1.1.md>";
        reference "ONF-TR-527, ONF-TR-512, ONF-TR-531, RFC 7950, RFC 6087 and ONF TAPI UML model
                  <https://github.com/OpenNetworkingFoundation/TAPI/tree/v2.1.1/UML>";
    }
    revision 2018-10-16 {
        description "ONF Transport API version 2.1.0.
                   Changes included in this TAPI release (v2.1.0) are listed in
                  <https://github.com/OpenNetworkingFoundation/TAPI/blob/develop/CHANGE_LOG/change-log.2.1.0.md>";
        reference "ONF-TR-527, ONF-TR-512, ONF-TR-531, RFC 7950, RFC 6087 and ONF TAPI UML model
                  <https://github.com/OpenNetworkingFoundation/TAPI/tree/v2.1.0/UML>";
    }
    revision 2018-03-07 {
        description "ONF Transport API version 2.0.2
        This YANG module has been generated from the TAPI UML Model using the IISOMI-Eagle xmi2yang mapping tool.
        Changes in this revision: <https://github.com/OpenNetworkingFoundation/TAPI/blob/develop/CHANGE_LOG/change-log.2.0.2.md>";
        reference "ONF-TR-527, ONF-TR-512, ONF-TR-531, RFC 6020, RFC 6087 and ONF TAPI UML model
                  <https://github.com/OpenNetworkingFoundation/TAPI/tree/v2.0.2/UML>";
    }
    revision 2018-02-16 {
        description "ONF Transport API version 2.0.1
        This YANG module has been generated from the TAPI UML Model using the IISOMI-Eagle xmi2yang mapping tool.
        Changes in this revision: <https://github.com/OpenNetworkingFoundation/TAPI/blob/develop/CHANGE_LOG/change-log.2.0.1.md>";
        reference "ONF-TR-527, ONF-TR-512, ONF-TR-531, RFC 6020, RFC 6087 and ONF TAPI UML model
                  <https://github.com/OpenNetworkingFoundation/TAPI/tree/v2.0.1/UML>";
    }
    revision 2018-01-02 {
        description "ONF Transport API version 2.0.0
        This YANG module has been generated from the TAPI UML Model using the IISOMI-Eagle xmi2yang mapping tool.
        Changes in this revision: <https://github.com/OpenNetworkingFoundation/TAPI/blob/develop/CHANGE_LOG/change-log.2.0.0.md>";
        reference "ONF-TR-527, ONF-TR-512, ONF-TR-531, RFC 6020, RFC 6087 and ONF TAPI UML model
                  <https://github.com/OpenNetworkingFoundation/TAPI/tree/v2.0.0/UML>";
    }
    augment "/tapi-common:context/tapi-notification:notification-context/tapi-notification:notification" {
        container alarm-info {
            uses alarm-info;
            description "none";
        }
        description "none";
    }
    augment "/tapi-common:context/tapi-notification:notification-context/tapi-notification:notification" {
        container tca-info {
            uses tca-info;
            description "none";
        }
        description "none";
    }
    /**************************
    * package object-classes
    **************************/ 
    grouping alarm-info {
        leaf alarm-name {
            type alarm-condition-name;
            description "The probable cause of the failure (detected fault).
                G.806:
                - fault: A fault is the inability of a function to perform a required action. This does not include an inability due to preventive maintenance, lack of external resources or planned actions.
                - fault cause: A single disturbance or fault may lead to the detection of multiple defects.
                - defect: The density of anomalies has reached a level where the ability to perform a required function has been interrupted.
                Defects are used as input for performance monitoring, the control of consequent actions and for the determination of fault causes.
                A fault cause is the result of a correlation process which is intended to identify the defect that is representative of the disturbance or fault that is causing the problem.
                - failure: The fault cause persisted long enough to consider the ability of an item to perform a required function to be terminated. The item may be considered as failed; a fault has now been detected.
                - alarm: A human-observable indication that draws attention to a failure (detected fault) usually giving an indication of the severity of the fault.";
        }
        leaf native-alarm-info {
            type string;
            description "The probable cause of the failure as shown by lower level controllers.";
        }
        leaf is-transient {
            type boolean;
            description "An alarm is transient when stateless, i.e. an explicit clear notification is not foreseen.";
        }
        leaf perceived-severity {
            type perceived-severity-type;
            description "The alarm severity.";
        }
        leaf service-affecting {
            type service-affecting;
            description "The impact on the service.";
        }
        leaf alarm-category {
            type alarm-category;
            description "The alarm category, based on ITU-T X.733.";
        }
        list alarm-qualifier {
            key 'value-name';
            uses tapi-common:name-and-value;
            description "Further information necessary to precisely/uniquely/unambiguously identify the alarm.
                For Equipment and Processing Alarm Category, e.g. the local id of the ActualNonFieldReplaceableModule which identifies exact alarm source.
                For Environment Alarm Category, e.g. on the same Device instance may appear more Environmental alarm notifications with same Alarn Name.
                For Connectivity Alarm Category in case that same CEP instance includes e.g. both OTS and OMS monitoring layers.";
        }
        description "This class augments the Notification class with alarm related parameters.";
    }
    grouping tca-info {
        leaf threshold-indicator-name {
            type tapi-common:pm-parameter-name;
            description "PM metric name which TCA refers to.";
        }
        leaf is-transient {
            type boolean;
            description "A threshold crossing alert is transient when stateless, i.e. an explicit clear notification is not foreseen.";
        }
        leaf perceived-tca-severity {
            type perceived-tca-severity;
            description "The threshold crossing alert severity.";
        }
        container threshold-observed-value {
            uses tapi-common:pm-parameter-value;
            description "The observed value of PM metric to which TCA refers to.";
        }
        container threshold-configured-value {
            uses tapi-common:pm-parameter-value;
            description "The configured threshold value of PM metric to which TCA refers to.";
        }
        leaf oam-job {
            type tapi-common:uuid;
            description "Reference to the OamJob instance for which the PM metric and threshold values were configured.
                The reference is defined as simple UUID because TapiFm does not import TapiOam.
                MEF 35.1: Identification of the PM Session for which the TCA Function was configured.";
        }
        description "This class augments the Notification class with threshold crossing alert related parameters.";
    }

    /**************************
    * package type-definitions
    **************************/ 
    identity ALARM_CATEGORY {
        description "none";
    }
    identity ALARM_CATEGORY_EQUIPMENT {
        base ALARM_CATEGORY;
        description "none";
    }
    identity ALARM_CATEGORY_ENVIRONMENT {
        base ALARM_CATEGORY;
        description "none";
    }
    identity ALARM_CATEGORY_CONNECTIVITY {
        base ALARM_CATEGORY;
        description "none";
    }
    identity ALARM_CATEGORY_TCA {
        base ALARM_CATEGORY;
        description "none";
    }
    identity ALARM_CATEGORY_PROCESSING {
        base ALARM_CATEGORY;
        description "none";
    }
    identity ALARM_CATEGORY_SECURITY {
        base ALARM_CATEGORY;
        description "none";
    }
    identity ALARM_CONDITION_NAME {
        description "none";
    }
    identity PERCEIVED_TCA_SEVERITY {
        description "none";
    }
    identity PERCEIVED_TCA_SEVERITY_WARNING {
        base PERCEIVED_TCA_SEVERITY;
        description "ITU-T G.7710/X.733/M.3100: Indication for a potential or impending service-affecting fault. Further diagnosis should be made.";
    }
    identity PERCEIVED_TCA_SEVERITY_CLEAR {
        base PERCEIVED_TCA_SEVERITY;
        description "Included only for some possible backward compatibility purpose. It should not be used to assign a severity to a failure.
            ITU-T G.7710: The severities 'cleared' and 'indeterminate' defined by [ITU-T X.733] are not included in Table 2, as it is assumed that these are not to be used to assign a failure.";
    }
    identity ALARM_NOTIFICATION_TYPE {
        description "none";
    }
    identity ALARM_NOTIFICATION_TYPE_ALARM_EVENT {
        base ALARM_NOTIFICATION_TYPE;
        description "The notification of an alarm event.";
    }
    identity ALARM_NOTIFICATION_TYPE_THRESHOLD_CROSSING_ALERT {
        base ALARM_NOTIFICATION_TYPE;
        description "The notification of a threshold crossing alert event.";
    }
    typedef alarm-category {
        type identityref {
            base ALARM_CATEGORY;
        }
        description "none";
    }
    typedef perceived-severity-type {
        type enumeration {
            enum CRITICAL {
                description "ITU-T G.7710/X.733/M.3100: Indication for a service-affecting condition. Immediate corrective action is required.";
            }
            enum MAJOR {
                description "ITU-T G.7710/X.733/M.3100: Indication for a service-affecting condition. Urgent corrective action is required.";
            }
            enum MINOR {
                description "ITU-T G.7710/X.733/M.3100: Indication for a non-service-affecting condition. Corrective action should be taken in order to prevent more serious fault.";
            }
            enum WARNING {
                description "ITU-T G.7710/X.733/M.3100: Indication for a potential or impending service-affecting fault. Further diagnosis should be made.";
            }
            enum CLEARED {
                description "Included only for some possible backward compatibility purpose. It should not be used to assign a severity to a failure.
                    ITU-T G.7710: The severities 'cleared' and 'indeterminate' defined by [ITU-T X.733] are not included in Table 2, as it is assumed that these are not to be used to assign a failure.";
            }
        }
        description "The types of perceived severity.
            ITU-T G.7710: Failures may have been categorized to indicate the severity or urgency of the fault.";
    }
    typedef service-affecting {
        type enumeration {
            enum SERVICE_AFFECTING {
                description "The service is affected by the failure.";
            }
            enum NOT_SERVICE_AFFECTING {
                description "The service is not affected by the failure.";
            }
            enum UNKNOWN {
                description "The impact on the service is unknown.";
            }
        }
        description "The possible impact on the service.";
    }
    typedef alarm-condition-name {
        type identityref {
            base ALARM_CONDITION_NAME;
        }
        description "The alarm condition name, or alarm probable cause.
            This extensible enumeration can be augmented with specific alarm condition names in the other modules.";
    }
    typedef perceived-tca-severity {
        type identityref {
            base PERCEIVED_TCA_SEVERITY;
        }
        description "The types of perceived severity of threshold crossing alerts.";
    }
    typedef alarm-notification-type {
        type identityref {
            base ALARM_NOTIFICATION_TYPE;
        }
        description "The list of alarm specific notification types.";
    }

}
