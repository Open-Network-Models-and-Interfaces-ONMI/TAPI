module tapi-notification-patch1 {
    yang-version "1.1";
    namespace "urn:onf:otcc:yang:tapi-notification-patch1";
    prefix tapi-notification-patch1;
    import tapi-common {
        prefix tapi-common;
    }
    import tapi-notification {
        prefix tapi-notification;
    }
    organization "ONF OTCC (Open Transport Configuration & Control) Project";
    contact "
         Project Web: <https://wiki.opennetworking.org/display/OTCC/TAPI>
         Project List: <mailto:transport-api@opennetworking.org>
         Editor: Karthik Sethuraman <mailto:karthik.sethuraman@necam.com>
         Andrea Mazzini <mailto:andrea.mazzini@nokia.com>
         Arturo Mayoral <mailto:arturo.mayoral@telefonica.com>
         Nigel Davis <mailto:ndavis@ciena.com>
         Ramon Casellas <mailto:ramon.casellas@cttc.es>";
    description "
        This module contains TAPI Notification Model definitions regarding patch 1.
        Copyright (c) 2023 Open Networking Foundation (ONF). All rights reserved.
        License: This module is distributed under the Apache License 2.0.";
    revision 2024-03-01 {
        description "ONF Transport API version 2.5.0.
                   Patch 1 described in
                   <https://github.com/OpenNetworkingFoundation/TAPI/tree/tapi-2_5_0-fixes>";
        reference "ONF-TR-527, ONF-TR-512, ONF-TR-531, RFC 7950, RFC 6087 and ONF TAPI UML model
                  <https://github.com/OpenNetworkingFoundation/TAPI/tree/v2.5.0/UML>";
    }
    /**************************
    * notification-subscription-service augment
    **************************/ 
    augment "/tapi-common:context/tapi-notification:notification-context/tapi-notification:notif-subscription" {
        container notification-references-by-name {
            uses notification-references-by-name;
            description "none";
        }
        description "none";
    }
    /**************************
    * definitions of references
    **************************/
    grouping notification-ref {
        leaf notification-uuid {
            type leafref {
                path '/tapi-common:context/tapi-notification:notification-context/tapi-notification:notification/tapi-notification:uuid';
            }
            description "none";
        }
        description "none";
    }
    grouping event-notification-ref {
        leaf event-notification-uuid {
            type leafref {
                path '/tapi-common:context/tapi-notification:notification-context/tapi-notification:event-notification/tapi-notification:uuid';
            }
            description "none";
        }
        description "none";
    }
    /**************************
    * package object-classes
    **************************/ 
    grouping notification-references-by-name {
        list notification {
            uses notification-ref;
            key 'notification-uuid';
            config false;
            description "The Notification instances associated to this NotificationSubscriptionService instance.";
        }
        list event-notification {
            uses event-notification-ref;
            key 'event-notification-uuid';
            config false;
            description "The EventNotification instances associated to this NotificationSubscriptionService instance.";
        }
        description "none";
    }
}
