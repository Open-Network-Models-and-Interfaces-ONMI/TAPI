module TapiOchSpec-ObjectClasses {
    namespace "uri:onf:TapiOchSpec-ObjectClasses";
    prefix TapiOchSpec-ObjectClasses;
    import TapiOchSpec-DataTypes {
        prefix TapiOchSpec-DataTypes;
    }
    import TapiSpec-ObjectClasses {
        prefix TapiSpec-ObjectClasses;
    }
    revision 2016-05-22{}
    grouping OchAdapterAndConnectionPointSpec {
        leaf monitoredDirection {
            type TapiOchSpec-DataTypes:MonitoredDirection;
            config false;
            description "This attribute indicates the monitored direction.  If the OCh_NonIntrusiveMonitoring instance is contained by OCh_ConnectionTerminationPointSource then the value is fixed to SOURCE.  If the OCh_NonIntrusiveMonitoring instance is contained by OCh_ConnectionTerminationPointSink then the value is fixed to SINK.  If the OCh_NonIntrusiveMonitoring instance is contained by OCh_ConnectionTerminationPointBidirectional then there is one instance that is fixed to SOURCE and one instance that is fixed to SINK.";
        }
    }
    list OchLpSpec {
        key 'lpSpecReference';
        config true;
        uses TapiSpec-ObjectClasses:LpSpec;
        container _adapterSpec {
            config true;
            uses OchAdapterAndConnectionPointSpec;
        }
        container _terminationSpec {
            config true;
            uses OchTerminationSpec;
        }
    }
    grouping OchTerminationSpec {
        container selectedApplicationIdentifier {
            description "This attribute indicates the selected Application Identifier that is used by the OCh trail termination function. The syntax of ApplicationIdentifier is a pair {ApplicationIdentifierType, PrintableString}. The value of ApplicationIdentifierType is either STANDARD or PROPRIETARY. The value of PrintableString represents the standard application code as defined in the ITU-T Recommendations or a vendor-specific proprietary code. If the ApplicationIdentifierType is STANDARD the value of PrintableString represents a standard application code as defined in the ITU-T Recommendations. If the ApplicationIdentifierType is PROPRIETARY, the first six characters of the PrintableString must contain the Hexadecimal representation of an OUI assigned to the vendor whose implementation generated the Application Identifier; the remaining octets of the PrintableString are unspecified. The value of this attribute of an object instance has to be one of the values identified in the attribute SupportableApplicationIdentifierList of the same object instance. The values and value ranges of the optical interface parameters of a standard application code must be consistent with those values specified in the ITU-T Recommendation for that application code.";
            config true;
            uses TapiOchSpec-DataTypes:ApplicationIdentifier;
        }
        container nominalCentralFrequencyOrWavelength {
            description "This attribute indicates the nominal central frequency or wavelength of the optical channel associated with the OCh Trail Termination function. The value of this attribute is a pair {LinkType, Integer}, in which LinkType is DWDM, or CWDM, or NO_WDM. When LinkType is DWDM, the integer represents the nominal central frequency in unit of MHz. When LinkType is CWDM, the integer represents the nominal central wavelength in unit of pm (picometer). When LinkType is NO_WDM, the Integer field is null. For frequency and wavelength, the value shall be within the range of the maximum and minimum central frequencies or wavelengths specified for the corresponding application code used at the OCh Trail Termination.
                This attribute is required for the OCh Trial Termination Point Source at the transmitter.  For the OCh Trail Termination Point Sink at the receiver, this attribute may not be needed since the receiver is required to operate at any frequency/wavelength between the maximum and minimum range for the standard application code.
                ";
            config true;
            uses TapiOchSpec-DataTypes:NominalCentralFrequencyOrWavelength;
        }
    }
}
