module TapiModule-Interfaces-Tapi_ConnectivityService {
    namespace 'urn:onf:TapiModule-Interfaces-Tapi_ConnectivityService';
    prefix TapiModule-Interfaces-Tapi_ConnectivityService;
    import TapiModule-ObjectClasses {
        prefix TapiModule-ObjectClasses;
    }
    rpc getConnectionDetails {
        input {
            leaf connectionId {
                type string;
            }
        }
        output {
            container connection {
                uses TapiModule-ObjectClasses:Tapi_Connection;
            }
        }
    }
    rpc getServiceList {
        output {
            list serviceList {
                uses TapiModule-ObjectClasses:Tapi_ConnectivityService;
            }
        }
    }
    rpc getConnectionEndPointDetails {
        input {
            leaf connEPId {
                type string;
            }
        }
        output {
            container connEP {
                uses TapiModule-ObjectClasses:Tapi_ConnectionEndPoint;
            }
        }
    }
    rpc getServiceEndPointDetails {
        input {
            leaf serviceEPId {
                type string;
            }
        }
        output {
            container serviceEP {
                uses TapiModule-ObjectClasses:Tapi_ServiceEndPoint;
            }
        }
    }
    rpc getServiceDetails {
        input {
            leaf serviceId {
                type string;
            }
        }
        output {
            container service {
                uses TapiModule-ObjectClasses:Tapi_ConnectivityService;
            }
        }
    }
    rpc getServiceEndPointList {
        output {
            list serviceEPList {
                uses TapiModule-ObjectClasses:Tapi_ServiceEndPoint;
            }
        }
    }
}
