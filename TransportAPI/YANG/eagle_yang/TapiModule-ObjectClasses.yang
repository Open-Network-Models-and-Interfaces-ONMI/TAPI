module TapiModule-ObjectClasses {
    namespace 'urn:onf:TapiModule-ObjectClasses';
    prefix TapiModule-ObjectClasses;
    grouping Tapi_Topology {
        leaf-list node {
            type string;
        }
        leaf-list link {
            type leafref {
                path '/Tapi_Link/undefined';
            }
        }
        leaf-list layerProtocolName {
            type string;
            min-elements 1;
        }
    }
    container Tapi_Context {
        config true;
        leaf topology {
            type leafref {
                path '/Tapi_Node/encapTopology/undefined';
            }
        }
    }
    grouping Tapi_Node {
        container encapTopology {
            config true;
            uses Tapi_Topology;
        }
        leaf-list nodeEdgePoint {
            type leafref {
                path '/Tapi_NodeEdgePoint/undefined';
            }
        }
        leaf-list layerProtocolName {
            type string;
            min-elements 1;
        }
    }
    list Tapi_Link {
        config true;
        uses Tapi_Link;
    }
    grouping Tapi_Link {
        list linkPort {
            key 'localIdList';
            config true;
            uses Tapi_LinkPort;
            min-elements 2;
        }
        leaf-list node {
            type string;
            min-elements 2;
        }
        leaf-list layerProtocolName {
            type string;
            min-elements 1;
        }
        leaf linkDirection {
            type string;
            description 'The directionality of the Link. 
                Is applicable to simple Links where all LinkEnds are BIDIRECTIONAL (the Link will be BIDIRECTIONAL) or UNIDIRECTIONAL (the Link will be UNIDIRECTIONAL). 
                Is not present in more complex cases.';
        }
    }
    list Tapi_NodeEdgePoint {
        config true;
        uses Tapi_NodeEdgePoint;
    }
    grouping Tapi_NodeEdgePoint {
        leaf-list layerProtocol {
            type string;
            min-elements 1;
        }
        leaf-list physicalPortReference {
            type string;
        }
    }
    list Tapi_ServiceEndPoint {
        config true;
        uses Tapi_ServiceEndPoint;
    }
    grouping Tapi_ServiceEndPoint {
        leaf-list layerProtocol {
            type string;
            min-elements 1;
        }
        leaf-list mappedNodeEdgePoint {
            type leafref {
                path '/Tapi_NodeEdgePoint/undefined';
            }
        }
    }
    container Tapi_ConnectionEndPoint {
        config true;
        uses Tapi_ConnectionEndPoint;
    }
    grouping Tapi_ConnectionEndPoint {
        leaf-list layerProtocol {
            type string;
            min-elements 1;
        }
        leaf-list clientNodeEdgePoint {
            type leafref {
                path '/Tapi_NodeEdgePoint/undefined';
            }
        }
        leaf serverNodeEdgePoint {
            type leafref {
                path '/Tapi_NodeEdgePoint/undefined';
            }
        }
        leaf peerConnectionEndPoint {
            type leafref {
                path '/Tapi_ConnectionEndPoint/undefined';
            }
        }
    }
    list Tapi_ConnectivityService {
        config true;
        uses Tapi_ConnectivityService;
    }
    grouping Tapi_ConnectivityService {
        list servicePort {
            key 'localIdList';
            config true;
            uses Tapi_ServicePort;
            min-elements 2;
        }
        leaf-list connection {
            type leafref {
                path '/Tapi_Path/lowerConnection/undefined';
            }
        }
        leaf layerProtocolName {
            type string;
        }
    }
    grouping Tapi_Connection {
        list connectionPort {
            key 'localIdList';
            config true;
            uses Tapi_ConnectionPort;
            min-elements 2;
        }
        list path {
            key 'localIdList';
            config true;
            uses Tapi_Path;
        }
        leaf node {
            type string;
        }
        leaf layerProtocolName {
            type string;
        }
    }
    grouping Tapi_Path {
        list lowerConnection {
            config true;
            uses Tapi_Connection;
            min-elements 1;
        }
    }
    grouping Tapi_LinkPort {
        leaf role {
            type string;
            description 'Each LinkEnd of the Link has a role (e.g., symmetric, hub, spoke, leaf, root)  in the context of the Link with respect to the Link function. ';
        }
        leaf direction {
            type string;
            description 'The orientation of defined flow at the LinkEnd.';
        }
        leaf nodeEdgePoint {
            type leafref {
                path '/Tapi_NodeEdgePoint/undefined';
            }
        }
    }
    grouping Tapi_ServicePort {
        leaf serviceEndPoint {
            type leafref {
                path '/Tapi_ServiceEndPoint/undefined';
            }
        }
        leaf role {
            type string;
            description 'Each EP of the FC has a role (e.g., working, protection, protected, symmetric, hub, spoke, leaf, root)  in the context of the FC with respect to the FC function. ';
        }
        leaf direction {
            type string;
            description 'The orientation of defined flow at the EndPoint.';
        }
    }
    grouping Tapi_ConnectionPort {
        leaf connectionEndPoint {
            type leafref {
                path '/Tapi_ConnectionEndPoint/undefined';
            }
        }
        leaf role {
            type string;
            description 'Each EP of the FC has a role (e.g., working, protection, protected, symmetric, hub, spoke, leaf, root)  in the context of the FC with respect to the FC function. ';
        }
        leaf direction {
            type string;
            description 'The orientation of defined flow at the EndPoint.';
        }
    }
}
