module TapiModule-Interfaces {
    namespace 'urn:onf:TapiModule-Interfaces';
    prefix TapiModule-Interfaces;
    container Tapi::TopologyService {
        config true;
        rpc getTopologyDetails {
            output {
                leaf topology {
                    type leafref {
                        path '/TapiModule-ObjectClasses/Tapi::Topology/localId';
                    }
                }
            }
            input {
                leaf topologyId {
                    type string;
                }
            }
        }
        rpc getNodeDetails {
            output {
                leaf node {
                    type leafref {
                        path '/TapiModule-ObjectClasses/Tapi::Node/localId';
                    }
                }
            }
            input {
                leaf nodeId {
                    type string;
                }
            }
        }
        rpc getLinkList {
            output {
                leaf-list linkList {
                    type leafref {
                        path '/TapiModule-ObjectClasses/Tapi::Link/localId';
                    }
                }
            }
            input {
                leaf topologyId {
                    type string;
                }
            }
        }
        rpc getNodeEdgePointDetails {
            output {
                leaf edgePoint {
                    type leafref {
                        path '/TapiModule-ObjectClasses/Tapi::NodeEdgePoint/localId';
                    }
                }
            }
            input {
                leaf nodeEPId {
                    type string;
                }
            }
        }
        rpc getLinkDetails {
            output {
                leaf link {
                    type leafref {
                        path '/TapiModule-ObjectClasses/Tapi::Link/localId';
                    }
                }
            }
            input {
                leaf linkId {
                    type string;
                }
            }
        }
        rpc getNodeList {
            output {
                leaf-list nodeList {
                    type leafref {
                        path '/TapiModule-ObjectClasses/Tapi::Node/localId';
                    }
                }
            }
            input {
                leaf topologyId {
                    type string;
                }
            }
        }
        rpc getNodeEdgePointList {
            output {
                leaf-list edgePointList {
                    type leafref {
                        path '/TapiModule-ObjectClasses/Tapi::NodeEdgePoint/localId';
                    }
                }
            }
            input {
                leaf nodeId {
                    type string;
                }
            }
        }
        rpc getLinkEndPointList {
            output {
                leaf-list edgePointList {
                    type leafref {
                        path '/TapiModule-ObjectClasses/Tapi::NodeEdgePoint/localId';
                    }
                }
            }
            input {
                leaf linkId {
                    type string;
                }
            }
        }
        rpc getAssociatedNodeListForLink {
            output {
                leaf-list nodeList {
                    type leafref {
                        path '/TapiModule-ObjectClasses/Tapi::Node/localId';
                    }
                }
            }
            input {
                leaf linkId {
                    type string;
                }
            }
        }
    }
    container Tapi::ConnectivityService {
        config true;
        rpc getConnectionDetails {
            output {
                leaf connection {
                    type leafref {
                        path '/TapiModule-ObjectClasses/Tapi::Connection/localId';
                    }
                }
            }
            input {
                leaf connectionId {
                    type string;
                }
            }
        }
        rpc getServiceList {
            output {
                leaf-list serviceList {
                    type leafref {
                        path '/TapiModule-ObjectClasses/Tapi::Service/localId';
                    }
                }
            }
        }
        rpc getConnectionEndPointDetails {
            output {
                leaf connEP {
                    type leafref {
                        path '/TapiModule-ObjectClasses/Tapi::ConnectionEndPoint/localId';
                    }
                }
            }
            input {
                leaf connEPId {
                    type string;
                }
            }
        }
        rpc getServiceEndPointDetails {
            output {
                leaf serviceEP {
                    type leafref {
                        path '/TapiModule-ObjectClasses/Tapi::ServiceEndPoint/localId';
                    }
                }
            }
            input {
                leaf serviceEPId {
                    type string;
                }
            }
        }
        rpc getServiceDetails {
            output {
                leaf service {
                    type leafref {
                        path '/TapiModule-ObjectClasses/Tapi::Service/localId';
                    }
                }
            }
            input {
                leaf serviceId {
                    type string;
                }
            }
        }
        rpc getConnectionEndPointList {
            output {
                leaf-list endPointList {
                    type leafref {
                        path '/TapiModule-ObjectClasses/Tapi::ConnectionEndPoint/localId';
                    }
                }
            }
            input {
                leaf parentNodeOrServiceEpId {
                    type string;
                }
            }
        }
        rpc getServiceEndPointList {
            output {
                leaf-list serviceEPList {
                    type leafref {
                        path '/TapiModule-ObjectClasses/Tapi::ServiceEndPoint/localId';
                    }
                }
            }
        }
        rpc getConnectionListForService {
            output {
                leaf-list connectionList {
                    type leafref {
                        path '/TapiModule-ObjectClasses/Tapi::Connection/localId';
                    }
                }
            }
            input {
                leaf serviceId {
                    type string;
                }
            }
        }
    }
}
