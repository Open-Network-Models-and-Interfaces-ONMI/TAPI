module TapiModule-TypeDefinitions {
    namespace 'urn:onf:TapiModule-TypeDefinitions';
    prefix TapiModule-TypeDefinitions;
    grouping Tapi_EndRole {
        leaf SYMMETRIC {
            type string;
            config false;
        }
        leaf ROOT {
            type string;
            config false;
        }
        leaf LEAF {
            type string;
            config false;
        }
    }
    grouping Tapi_LayerProtocolName {
        leaf ETH {
            type string;
            config false;
        }
        leaf MPLS-TP {
            type string;
            config false;
        }
        leaf ODU {
            type string;
            config false;
        }
        leaf OCH {
            type string;
            config false;
        }
    }
}
