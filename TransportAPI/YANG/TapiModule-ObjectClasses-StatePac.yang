module TapiModule-ObjectClasses-StatePac {
    namespace "uri:onf:TapiModule-ObjectClasses-StatePac";
    prefix TapiModule-ObjectClasses-StatePac;
    import TapiModule-TypeDefinitions {
        prefix TapiModule-TypeDefinitions;
    }
    revision 2016-03-15{}
    grouping G_Tapi_AdminStatePac {
        leaf administrativeState {
            type TapiModule-TypeDefinitions:Tapi_AdministrativeState;
        }
        leaf operationalState {
            type TapiModule-TypeDefinitions:Tapi_OperationalState;
        }
        leaf lifecycleState {
            type TapiModule-TypeDefinitions:Tapi_LifecycleState;
        }
    }
    grouping G_Tapi_OperationalStatePac {
        leaf operationalState {
            type TapiModule-TypeDefinitions:Tapi_OperationalState;
        }
        leaf lifecycleState {
            type TapiModule-TypeDefinitions:Tapi_LifecycleState;
        }
    }
    grouping G_Tapi_LifecycleStatePac {
        leaf lifecycleState {
            type TapiModule-TypeDefinitions:Tapi_LifecycleState;
        }
    }
}
