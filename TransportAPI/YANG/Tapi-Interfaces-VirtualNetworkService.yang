module Tapi-Interfaces-VirtualNetworkService {
    namespace "uri:onf:Tapi-Interfaces-VirtualNetworkService";
    prefix Tapi-Interfaces-VirtualNetworkService;
    import Tapi-ObjectClasses {
        prefix Tapi-ObjectClasses;
    }
    revision 2016-05-23{}
    rpc createVirtualNetworkService {
        input {
            list servicePort {
                uses Tapi-ObjectClasses:VirtualNetworkServicePort;
                min-elements 2;
            }
            container vnwConstraint {
                uses Tapi-ObjectClasses:VirtualNetworkConstraint;
            }
            container connSchedule {
                uses Tapi-ObjectClasses:ScheduleInfo;
            }
        }
        output {
            container vnwService {
                uses Tapi-ObjectClasses:VirtualNetworkService;
            }
        }
    }
    rpc deleteVirtualNetworkService {
        input {
            leaf serviceIdOrName {
                type string;
            }
        }
        output {
            container vnwService {
                uses Tapi-ObjectClasses:VirtualNetworkService;
            }
        }
    }
    rpc getVirtualNetworkServiceDetails {
        input {
            leaf serviceIdOrName {
                type string;
            }
        }
        output {
            container vnwService {
                uses Tapi-ObjectClasses:VirtualNetworkService;
            }
        }
    }
    rpc getVirtualNetworkServiceList {
        output {
            list vnwService {
                uses Tapi-ObjectClasses:VirtualNetworkService;
            }
        }
    }
}
