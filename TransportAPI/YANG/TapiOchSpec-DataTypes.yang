module TapiOchSpec-DataTypes {
    namespace "uri:onf:TapiOchSpec-DataTypes";
    prefix TapiOchSpec-DataTypes;
    revision 2016-05-23{}
    grouping ApplicationIdentifier {
        leaf applicationIdentifierType {
            type string;
        }
        leaf applicationIdentifierValue {
            type string;
        }
    }
    typedef MonitoredDirection {
        description "The enumeration with the options for directionality for nonintrusive monitoring.";
        type enumeration {
            enum SINK;
            enum SOURCE;
        }
    }
    grouping NominalCentralFrequencyOrWavelength {
        leaf linkType {
            type string;
        }
        leaf nominalCentralFrequencyOrWavelength {
            type string;
        }
    }
}
