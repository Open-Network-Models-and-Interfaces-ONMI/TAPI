module TapiConnectivityService {

  namespace "urn:onf:Tapi:ConnectivityService:yang";
  prefix TapiConnectivityService;
  
  import TapiInformationModel { prefix Tapi; }
  import TapiDataTypes { prefix TapiDt; }
  
  organization "ONF T-API Group";

  contact "mailto:info@opennetworking.org";

  description
    "This module contains a collection of YANG definitions for
     Connectivity Service. It is part of the T-API
     specification. 
     Authors List:
     Ricard Vilalta (CTTC)
     Victor López (Telefónica)
     (T-API Team)";
   
  revision 2015-09-11 {
    description
      "First draft for Transport API Connectivity Service";
  }
   
  
  /*****************************************************************
  * RPC definitions
  *****************************************************************/
  rpc getServiceEndPointList {
    input {
      description "node-id";
      leaf uuid{
        type TapiDt:UniversalId;
      }
    }
    output {
      list endPointList {
        key "uuid";
        uses Tapi:ServiceEndPoint;
      }
    }
  }
  
  rpc getServiceList {
    input {
      description "node id";
      leaf uuid{
        type TapiDt:UniversalId;
      }
    }
    output {
      leaf-list service-list {
        type leafref {
          path "/Tapi:ConnectivityService/Tapi:uuid";
        }
      }
    }
  }
  
  rpc getConnectionList {
    input {
      description "node id";
      leaf uuid{
        type TapiDt:UniversalId;
      }
    }
    output {
      leaf-list connectionList {
        type leafref {
          path "/Tapi:ConnectivityService/Tapi:connection/Tapi:uuid";
        }
      }
    }
  }
  
  rpc getServiceDetails {
    input {
      description "service id";
      leaf uuid{
        type TapiDt:UniversalId;
      }
    }
  
    output {
      container service {
        uses Tapi:ConnectivityService;
      }
    }
  }
  
  rpc getConnectionDetails {
    input {
      description "connection id";
      leaf uuid{
        type TapiDt:UniversalId;
      }
    }
    output {
      container connection{
        uses Tapi:Connection;
      }
    }
  }
  
  rpc getPathDetails {
    input {
      description "connection id";
      leaf uuid{
        type TapiDt:UniversalId;
      }
    }
    output {
      leaf-list pathList {
        type leafref {
          path "/Tapi:ConnectivityService/Tapi:connection/Tapi:path/Tapi:uuid";
        }
      }
    }
  }
  
  rpc getServiceEndPointDetails {
    input {
      description "service end point id";
      leaf uuid{
        type TapiDt:UniversalId;
      }
    }
    output {
      container serviceEndPoint {
        uses Tapi:ServiceEndPoint;
      }
    }
  }
  
  rpc getConnectionEndPointDetails {
    input {
      description "connection end point id";
      leaf uuid{
        type TapiDt:UniversalId;
      }
    }
    output {
      container connectionEndPoint {
        uses Tapi:ConnectionEndPoint;
      }
    }
  }
 
}
