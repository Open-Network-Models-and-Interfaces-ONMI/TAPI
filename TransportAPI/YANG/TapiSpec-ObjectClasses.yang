module TapiSpec-ObjectClasses {
    namespace "uri:onf:TapiSpec-ObjectClasses";
    prefix TapiSpec-ObjectClasses;
    revision 2016-05-23{}
    grouping LpSpec {
        leaf lpSpecReference {
            type string;
        }
    }
    grouping LtpSpec {
        leaf ltpSpecReference {
            type string;
        }
        leaf-list lpSpecReference {
            type string;
            min-elements 1;
        }
    }
}
