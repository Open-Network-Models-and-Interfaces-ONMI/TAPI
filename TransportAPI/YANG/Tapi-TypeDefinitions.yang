module Tapi-TypeDefinitions {
    namespace "uri:onf:Tapi-TypeDefinitions";
    prefix Tapi-TypeDefinitions;
    revision 2016-05-22{}
    typedef ServiceType {
        type enumeration {
            enum POINT_TO_POINT_CONNECTIVITY;
            enum POINT_TO_MULTIPOINT_CONNECTIVTY;
            enum MULTIPOINT_CONNECTIVITY;
        }
    }
    typedef FixedCapacityValue {
        type enumeration {
            enum NOT_APPLICABLE;
            enum 10MBPS;
            enum 100MBPS;
            enum 1GBPS;
            enum 2.4GBPS;
            enum 10GBPS;
            enum 40GBPS;
            enum 100GBPS;
            enum 200GBPS;
            enum 400GBPS;
        }
    }
    typedef PortRole {
        type enumeration {
            enum SYMMETRIC;
            enum ROOT;
            enum LEAF;
        }
    }
    typedef LayerProtocolName {
        type enumeration {
            enum OCH;
            enum ODU;
            enum ETH;
            enum MPLS_TP;
        }
    }
    grouping NameAndValue {
        leaf valueName {
            type string;
            description "The name of the value. The value need not have a name.";
        }
        leaf value {
            type string;
            description "The value";
        }
    }
    typedef UniversalId {
        type string;
    }
    typedef ForwardingDirection {
        type enumeration {
            enum BIDIRECTIONAL;
            enum UNIDIRECTIONAL;
            enum UNDEFINED_OR_UNKNOWN;
        }
    }
    typedef TerminationDirection {
        type enumeration {
            enum BIDIRECTIONAL;
            enum SINK;
            enum SOURCE;
            enum UNDEFINED_OR_UNKNOWN;
        }
    }
    typedef PortDirection {
        type enumeration {
            enum BIDIRECTIONAL;
            enum INPUT;
            enum OUTPUT;
            enum UNIDENTIFIED_OR_UNKNOWN;
        }
    }
    typedef OperationalState {
        type enumeration {
            enum DISABLED;
            enum ENABLED;
        }
    }
    typedef AdministrativeState {
        type enumeration {
            enum LOCKED;
            enum UNLOCKED;
        }
    }
    typedef LifecycleState {
        type enumeration {
            enum PLANNED;
            enum POTENTIAL;
            enum INSTALLED;
            enum PENDING_REMOVAL;
        }
    }
    typedef TerminationState {
        type enumeration {
            enum LP_CAN_NEVER_TERMINATE;
            enum LT_NOT_TERMINATED;
            enum TERMINATED_SERVER_TO_CLIENT_FLOW;
            enum TERMINATED_CLIENT_TO_SERVER_FLOW;
            enum TERMINATED_BIDIRECTIONAL;
            enum LT_PERMENANTLY_TERMINATED;
            enum TERMINATION_STATE_UNKNOWN;
        }
    }
    grouping Capacity {
        leaf totalSize {
            type string;
            description "Total capacity of the TopologicalEntity in MB/s";
        }
        leaf maximumUsageInstances {
            type string;
            description "Where there is some limit to the number of client (e.g. in a channelized case).";
        }
        leaf maximumUsageSize {
            type string;
            description "Where a client is of variable capacity but due to some underlying realization the maximum size of the client is smaller than the totalSize.";
        }
        leaf numberingRange {
            type string;
            description "Method for identifying units of capacity via some numbering scheme.";
        }
    }
    grouping CostCharacteristic {
        leaf costName {
            type string;
            description "The cost characteristic will related to some aspect of the TopologicalEntity (e.g. $ cost, routing weight). This aspect will be conveyed by the costName.";
        }
        leaf costValue {
            type string;
            description "The specific cost.";
        }
        leaf costAlgorithm {
            type string;
            description "The cost may vary based upon some properties of the TopologicalEntity. The rules for the variation are conveyed by the costAlgorithm.";
        }
    }
    grouping QueuingLatency {
        leaf trafficPropertyName {
            type string;
            description "The identifier of the specific traffic property to which the queuing latency applies.";
        }
        leaf latencyValue {
            type string;
            description "The specific queuing latency for the traffic property.";
        }
    }
    grouping RiskCharacteristic {
        leaf riskCharacteristicName {
            type string;
            description "The name of the risk characteristic. The characteristic may be related to a specific degree of closeness. 
                For example a particular characteristic may apply to failures that are localized (e.g. to one side of a road) where as another characteristic may relate to failures that have a broader impact (e.g. both sides of a road that crosses a bridge).
                Depending upon the importance of the traffic being routed different risk characteristics will be evaluated.";
        }
        leaf-list riskIdentifierList {
            description "A list of the identifiers of each physical/geographic unit (with the specific risk characteristic) that is related to a segment of the TopologicalEntity.";
            ordered-by system;
            type string;
            min-elements 1;
        }
    }
    grouping ValidationMechanism {
        leaf validationMechanism {
            type string;
            description "Name of mechanism used to validate adjacency";
        }
        leaf layerProtocolAdjacencyValidated {
            type string;
            description "State of validatiion";
        }
        leaf validationRobustness {
            type string;
            description "Quality of validation (i.e. how likely is the stated validation to be invalid)";
        }
    }
    typedef DirectiveValue {
        type enumeration {
            enum MINIMIZE;
            enum MAXIMIZE;
            enum ALLOW;
            enum DISALLOW;
            enum DONT_CARE;
        }
    }
    typedef DateAndTime {
        type string;
    }
}
