module Tapi_OchSpec-DataTypes {
    namespace "uri:onf:Tapi_OchSpec-DataTypes";
    prefix Tapi_OchSpec-DataTypes;
    revision 2016-05-09{}
    grouping ApplicationIdentifier {
        description "lifecycle:Experimental";
        leaf applicationIdentifierType {
            type string;
        }
        leaf applicationIdentifierValue {
            type string;
        }
    }
    typedef MonitoredDirection {
        description "lifecycle:Experimental";
        type enumeration {
            enum SINK;
            enum SOURCE;
        }
    }
    grouping NominalCentralFrequencyOrWavelength {
        description "lifecycle:Experimental";
        leaf linkType {
            type string;
        }
        leaf nominalCentralFrequencyOrWavelength {
            type string;
        }
    }
}
