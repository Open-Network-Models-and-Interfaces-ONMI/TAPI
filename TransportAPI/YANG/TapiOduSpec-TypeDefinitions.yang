module TapiOduSpec-TypeDefinitions {
    namespace "uri:onf:TapiOduSpec-TypeDefinitions";
    prefix TapiOduSpec-TypeDefinitions;
    revision 2016-05-22{}
    typedef BitString {
        type string;
    }
    grouping DegThr {
        leaf degThrValue {
            type string;
            description "Percentage of detected errored blocks";
        }
        leaf degThrType {
            type string;
            description "Number of errored blocks";
        }
        leaf percentageGranularity {
            type string;
        }
    }
    typedef ODUk_TtpKBitRate {
        type enumeration {
            enum 1.25_G;
            enum 2.5_G;
            enum 10_G;
            enum 10_G_2E;
            enum 40_G;
            enum 100_G;
            enum FLEX_CBR;
            enum FLEX_GFP;
        }
    }
    typedef ODUk_TcmOrGccChoice {
        type string;
    }
    typedef TimDetMo {
        type enumeration {
            enum DAPI;
            enum SAPI;
            enum BOTH;
        }
    }
    typedef ODUk_h_ResizingProtocolStatus {
        type enumeration {
            enum LCR_INITIATED;
            enum LCR_FAILED;
            enum LCR_COMPLETED;
            enum BWR_INITIATED;
            enum BWR_COMPLETED;
        }
    }
    typedef ODUk_CtpProblemList {
        type enumeration {
            enum PLM;
            enum MSIM;
            enum LOF_LOM;
            enum LOOMFI;
        }
    }
    typedef ODUk_CtpKBitRate {
        type enumeration {
            enum 1.25_G;
            enum 2.5_G;
            enum 10_G;
            enum 10_G_2E;
            enum 40_G;
            enum 100_G;
            enum FLEX_CBR;
            enum FLEX_GFP;
        }
    }
    grouping ODUk_h_nominalBitRateAndTolerance {
        leaf tolerance {
            type uint64;
            description "tolerance in ppm";
        }
        leaf frequency {
            type string;
            description "frequency in kilohertz";
        }
    }
    typedef TcmMode {
        type enumeration {
            enum OPERATIONAL;
            enum TRANSPARENT;
            enum MONITOR;
        }
    }
    typedef ODUkT_tcmExtension {
        type enumeration {
            enum NORMAL;
            enum PASS-THROUGH;
            enum ERASE;
        }
    }
    typedef ODUkT_AdministrationState {
        type enumeration {
            enum LOCKED;
            enum NORMAL;
        }
    }
    typedef ODUk_TcmStatus {
        type enumeration {
            enum NO_SOURCE_TC;
            enum IN_USE_WITHOUT_IAE;
            enum IN_USE_WITH_IAE;
            enum RESERVED_1;
            enum RESERVED_2;
            enum LCK;
            enum OCI;
            enum AIS;
        }
    }
}
