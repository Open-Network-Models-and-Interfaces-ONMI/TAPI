module Tapi-Interfaces-ConnectivityService {
    namespace "uri:onf:Tapi-Interfaces-ConnectivityService";
    prefix Tapi-Interfaces-ConnectivityService;
    import Tapi-ObjectClasses {
        prefix Tapi-ObjectClasses;
    }
    revision 2016-05-22{}
    rpc getConnectionDetails {
        input {
            leaf serviceIdOrName {
                type string;
            }
            leaf connectionIdOrName {
                type string;
            }
        }
        output {
            container connection {
                uses Tapi-ObjectClasses:Connection;
            }
        }
    }
    rpc getConnectivityServiceList {
        output {
            list connService {
                ordered-by system;
                uses Tapi-ObjectClasses:ConnectivityService;
            }
        }
    }
    rpc getConnectionEndPointDetails {
        input {
            leaf serviceIdOrName {
                type string;
            }
            leaf connectionIdOrName {
                type string;
            }
            leaf connEPIdOrName {
                type string;
            }
        }
        output {
            container connEP {
                uses Tapi-ObjectClasses:ConnectionEndPoint;
            }
        }
    }
    rpc getServiceEndPointDetails {
        input {
            leaf serviceEPIdOrName {
                type string;
            }
        }
        output {
            container serviceEndPoint {
                uses Tapi-ObjectClasses:ServiceEndPoint;
            }
        }
    }
    rpc getConnectivityServiceDetails {
        input {
            leaf serviceIdOrName {
                type string;
            }
        }
        output {
            container connService {
                uses Tapi-ObjectClasses:ConnectivityService;
            }
        }
    }
    rpc getServiceEndPointList {
        output {
            list serviceEndPoint {
                ordered-by system;
                uses Tapi-ObjectClasses:ServiceEndPoint;
            }
        }
    }
    rpc createConnectivityService {
        input {
            list servicePort {
                ordered-by system;
                uses Tapi-ObjectClasses:ConnectivityServicePort;
                min-elements 2;
            }
            container connConstraint {
                uses Tapi-ObjectClasses:ConnectivityConstraint;
            }
            container connSchedule {
                uses Tapi-ObjectClasses:ScheduleInfo;
            }
        }
        output {
            container connService {
                uses Tapi-ObjectClasses:ConnectivityService;
            }
        }
    }
    rpc updateConnectivityService {
        input {
            leaf serviceIdOrName {
                type string;
            }
            container connConstraint {
                uses Tapi-ObjectClasses:ConnectivityConstraint;
            }
            container connSchedule {
                uses Tapi-ObjectClasses:ScheduleInfo;
            }
        }
        output {
            container connService {
                uses Tapi-ObjectClasses:ConnectivityService;
            }
        }
    }
    rpc deleteConnectivityService {
        input {
            leaf serviceIdOrName {
                type string;
            }
        }
        output {
            container connService {
                uses Tapi-ObjectClasses:ConnectivityService;
            }
        }
    }
}
