module Tapi-Interfaces-TopologyService {
    namespace "uri:onf:Tapi-Interfaces-TopologyService";
    prefix Tapi-Interfaces-TopologyService;
    import Tapi-ObjectClasses {
        prefix Tapi-ObjectClasses;
    }
    revision 2016-05-23{}
    rpc getTopologyDetails {
        input {
            leaf topologyIdOrName {
                type string;
            }
        }
        output {
            container topology {
                uses Tapi-ObjectClasses:Topology;
            }
        }
    }
    rpc getNodeDetails {
        input {
            leaf topologyIdOrName {
                type string;
            }
            leaf nodeIdOrName {
                type string;
            }
        }
        output {
            container node {
                uses Tapi-ObjectClasses:Node;
            }
        }
    }
    rpc getNodeEdgePointDetails {
        input {
            leaf topologyIdOrName {
                type string;
            }
            leaf nodeIdOrName {
                type string;
            }
            leaf epIdOrName {
                type string;
            }
        }
        output {
            container nodeEdgePoint {
                uses Tapi-ObjectClasses:NodeEdgePoint;
            }
        }
    }
    rpc getLinkDetails {
        input {
            leaf topologyIdOrName {
                type string;
            }
            leaf linkIdOrName {
                type string;
            }
        }
        output {
            container link {
                uses Tapi-ObjectClasses:Link;
            }
        }
    }
    rpc getTopologyList {
        output {
            list topology {
                uses Tapi-ObjectClasses:Topology;
            }
        }
    }
}
