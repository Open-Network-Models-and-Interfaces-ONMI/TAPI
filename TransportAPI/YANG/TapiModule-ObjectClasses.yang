module TapiModule-ObjectClasses {
    namespace "uri:onf:TapiModule-ObjectClasses";
    prefix TapiModule-ObjectClasses;
    import TapiModule-TypeDefinitions {
        prefix TapiModule-TypeDefinitions;
    }
    import TapiModule-ObjectClasses-StatePac {
        prefix TapiModule-ObjectClasses-StatePac;
    }
    revision 2016-03-15{}
    list Tapi_Topology {
        key 'uuid';
        config true;
        ordered-by system;
        uses G_Tapi_Topology;
    }
    grouping G_Tapi_Topology {
        list _node {
            key 'uuid';
            config true;
            ordered-by system;
            uses G_Tapi_Node;
        }
        list _link {
            key 'uuid';
            config true;
            ordered-by system;
            uses G_Tapi_Link;
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            key 'valueName';
            config true;
            ordered-by system;
            uses TapiModule-TypeDefinitions:G_Tapi_NameAndValue;
            min-elements 1;
        }
        list label {
            description "List of labels.A property of an entity with a value that is not expected to be unique and is allowed to change. A label carries no semantics with respect to the purpose of the entity and has no effect on the entity behavior or state.";
            key 'valueName';
            config true;
            ordered-by system;
            uses TapiModule-TypeDefinitions:G_Tapi_NameAndValue;
        }
        list extension {
            description "List of simple name-value extentions. Extension provides an opportunity to define properties not declared in the class that extend the class enabling a realization with simple ad-hoc extension of standard classes to be conformant.";
            key 'valueName';
            config true;
            ordered-by system;
            uses TapiModule-TypeDefinitions:G_Tapi_NameAndValue;
        }
        leaf-list layerProtocolName {
            ordered-by system;
            type TapiModule-TypeDefinitions:Tapi_LayerProtocolName;
            min-elements 1;
        }
    }
    list G_Tapi_Context {
        key 'uuid';
        config true;
        leaf _topology {
            type leafref {
                path '/Tapi_Topology/uuid';
            }
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            key 'valueName';
            config true;
            ordered-by system;
            uses TapiModule-TypeDefinitions:G_Tapi_NameAndValue;
            min-elements 1;
        }
        list label {
            description "List of labels.A property of an entity with a value that is not expected to be unique and is allowed to change. A label carries no semantics with respect to the purpose of the entity and has no effect on the entity behavior or state.";
            key 'valueName';
            config true;
            ordered-by system;
            uses TapiModule-TypeDefinitions:G_Tapi_NameAndValue;
        }
        list extension {
            description "List of simple name-value extentions. Extension provides an opportunity to define properties not declared in the class that extend the class enabling a realization with simple ad-hoc extension of standard classes to be conformant.";
            key 'valueName';
            config true;
            ordered-by system;
            uses TapiModule-TypeDefinitions:G_Tapi_NameAndValue;
        }
    }
    grouping G_Tapi_Node {
        uses G_Tapi_GlobalComponent;
        list _ownedNodeEdgePoint {
            key 'uuid';
            config true;
            ordered-by system;
            uses G_Tapi_NodeEdgePoint;
        }
        leaf-list _aggregatedNodeEdgePoint {
            ordered-by system;
            type leafref {
                path '/Tapi_Topology/_node/_ownedNodeEdgePoint/uuid';
            }
        }
        leaf _encapTopology {
            type leafref {
                path '/Tapi_Topology/uuid';
            }
        }
        container _stateSpec {
            config true;
            uses TapiModule-ObjectClasses-StatePac:G_Tapi_AdminStatePac;
        }
        container _transferCapacitySpec {
            config true;
            uses G_Tapi_TransferCapacityPac;
        }
        container _transferCostSpec {
            config true;
            uses G_Tapi_TransferCostPac;
        }
        container _transferIntegritySpec {
            config true;
            uses G_Tapi_TransferIntegrityPac;
        }
        container _transferTimingSpec {
            config true;
            uses G_Tapi_TransferTimingPac;
        }
        leaf-list layerProtocolName {
            ordered-by system;
            type TapiModule-TypeDefinitions:Tapi_LayerProtocolName;
            min-elements 1;
        }
    }
    grouping G_Tapi_Link {
        uses G_Tapi_GlobalComponent;
        list _linkPort {
            key 'localId';
            config true;
            ordered-by system;
            uses G_Tapi_LinkPort;
            min-elements 2;
        }
        leaf-list _node {
            ordered-by system;
            type leafref {
                path '/Tapi_Topology/_node/uuid';
            }
            min-elements 2;
        }
        container _stateSpec {
            config true;
            uses TapiModule-ObjectClasses-StatePac:G_Tapi_AdminStatePac;
        }
        container _transferCapacitySpec {
            config true;
            uses G_Tapi_TransferCapacityPac;
        }
        container _transferCostSpec {
            config true;
            uses G_Tapi_TransferCostPac;
        }
        container _transferIntegritySpec {
            config true;
            uses G_Tapi_TransferIntegrityPac;
        }
        container _transferTimingSpec {
            config true;
            uses G_Tapi_TransferTimingPac;
        }
        container _riskParameterSpec {
            config true;
            uses G_Tapi_RiskParameterPac;
        }
        container _validationSpec {
            config true;
            uses G_Tapi_ValidationPac;
        }
        container _lpTransitionSpec {
            config true;
            uses G_Tapi_LayerProtocolTransitionPac;
        }
        leaf-list layerProtocolName {
            ordered-by system;
            type TapiModule-TypeDefinitions:Tapi_LayerProtocolName;
            min-elements 1;
        }
        leaf direction {
            type TapiModule-TypeDefinitions:Tapi_ForwardingDirection;
            description "The directionality of the Link. 
                Is applicable to simple Links where all LinkEnds are BIDIRECTIONAL (the Link will be BIDIRECTIONAL) or UNIDIRECTIONAL (the Link will be UNIDIRECTIONAL). 
                Is not present in more complex cases.";
        }
    }
    grouping G_Tapi_NodeEdgePoint {
        list _layerProtocol {
            key 'localId';
            config true;
            ordered-by system;
            uses G_Tapi_LayerProtocol;
            min-elements 1;
        }
        leaf-list _clientNodeEdgePoint {
            ordered-by system;
            type string;
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            key 'valueName';
            config true;
            ordered-by system;
            uses TapiModule-TypeDefinitions:G_Tapi_NameAndValue;
            min-elements 1;
        }
        list label {
            description "List of labels.A property of an entity with a value that is not expected to be unique and is allowed to change. A label carries no semantics with respect to the purpose of the entity and has no effect on the entity behavior or state.";
            key 'valueName';
            config true;
            ordered-by system;
            uses TapiModule-TypeDefinitions:G_Tapi_NameAndValue;
        }
        list extension {
            description "List of simple name-value extentions. Extension provides an opportunity to define properties not declared in the class that extend the class enabling a realization with simple ad-hoc extension of standard classes to be conformant.";
            key 'valueName';
            config true;
            ordered-by system;
            uses TapiModule-TypeDefinitions:G_Tapi_NameAndValue;
        }
        leaf direction {
            type TapiModule-TypeDefinitions:Tapi_TerminationDirection;
        }
        leaf administrativeState {
            type TapiModule-TypeDefinitions:Tapi_AdministrativeState;
        }
        leaf operationalState {
            type TapiModule-TypeDefinitions:Tapi_OperationalState;
        }
        leaf lifecycleState {
            type TapiModule-TypeDefinitions:Tapi_LifecycleState;
        }
    }
    list Tapi_ServiceEndPoint {
        key 'uuid';
        config true;
        ordered-by system;
        uses G_Tapi_ServiceEndPoint;
    }
    grouping G_Tapi_ServiceEndPoint {
        list _layerProtocol {
            key 'localId';
            config true;
            ordered-by system;
            uses G_Tapi_LayerProtocol;
            min-elements 1;
        }
        leaf-list _mappedNodeEdgePoint {
            ordered-by system;
            type leafref {
                path '/Tapi_Topology/_node/_ownedNodeEdgePoint/uuid';
            }
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list label {
            description "List of labels.A property of an entity with a value that is not expected to be unique and is allowed to change. A label carries no semantics with respect to the purpose of the entity and has no effect on the entity behavior or state.";
            key 'valueName';
            config true;
            ordered-by system;
            uses TapiModule-TypeDefinitions:G_Tapi_NameAndValue;
        }
        list name {
            description "List of names. A property of an entity with a value that is unique in some namespace but may change during the life of the entity. A name carries no semantics with respect to the purpose of the entity.";
            key 'valueName';
            config true;
            ordered-by system;
            uses TapiModule-TypeDefinitions:G_Tapi_NameAndValue;
            min-elements 1;
        }
        list extension {
            description "List of simple name-value extentions. Extension provides an opportunity to define properties not declared in the class that extend the class enabling a realization with simple ad-hoc extension of standard classes to be conformant.";
            key 'valueName';
            config true;
            ordered-by system;
            uses TapiModule-TypeDefinitions:G_Tapi_NameAndValue;
        }
        leaf direction {
            type TapiModule-TypeDefinitions:Tapi_TerminationDirection;
        }
        leaf operationalState {
            type TapiModule-TypeDefinitions:Tapi_OperationalState;
        }
    }
    list Tapi_ConnectionEndPoint {
        key 'uuid';
        config true;
        ordered-by system;
        uses G_Tapi_ConnectionEndPoint;
    }
    grouping G_Tapi_ConnectionEndPoint {
        list _layerProtocol {
            key 'localId';
            config true;
            ordered-by system;
            uses G_Tapi_LayerProtocol;
            min-elements 1;
        }
        leaf-list _clientNodeEdgePoint {
            ordered-by system;
            type leafref {
                path '/Tapi_Topology/_node/_ownedNodeEdgePoint/uuid';
            }
        }
        leaf _serverNodeEdgePoint {
            type leafref {
                path '/Tapi_Topology/_node/_ownedNodeEdgePoint/uuid';
            }
        }
        leaf _peerConnectionEndPoint {
            type leafref {
                path '/Tapi_ConnectionEndPoint/uuid';
            }
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list label {
            description "List of labels.A property of an entity with a value that is not expected to be unique and is allowed to change. A label carries no semantics with respect to the purpose of the entity and has no effect on the entity behavior or state.";
            key 'valueName';
            config true;
            ordered-by system;
            uses TapiModule-TypeDefinitions:G_Tapi_NameAndValue;
        }
        list name {
            description "List of names. A property of an entity with a value that is unique in some namespace but may change during the life of the entity. A name carries no semantics with respect to the purpose of the entity.";
            key 'valueName';
            config true;
            ordered-by system;
            uses TapiModule-TypeDefinitions:G_Tapi_NameAndValue;
            min-elements 1;
        }
        list extension {
            description "List of simple name-value extentions. Extension provides an opportunity to define properties not declared in the class that extend the class enabling a realization with simple ad-hoc extension of standard classes to be conformant.";
            key 'valueName';
            config true;
            ordered-by system;
            uses TapiModule-TypeDefinitions:G_Tapi_NameAndValue;
        }
        leaf direction {
            type TapiModule-TypeDefinitions:Tapi_TerminationDirection;
        }
        leaf operationalState {
            type TapiModule-TypeDefinitions:Tapi_OperationalState;
        }
    }
    list Tapi_ConnectivityService {
        key 'uuid';
        config true;
        ordered-by system;
        uses G_Tapi_ConnectivityService;
    }
    grouping G_Tapi_ConnectivityService {
        list _servicePort {
            key 'localId';
            config true;
            ordered-by system;
            uses G_Tapi_ServicePort;
            min-elements 2;
        }
        list _connection {
            key 'uuid';
            config true;
            ordered-by system;
            uses G_Tapi_Connection;
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            key 'valueName';
            config true;
            ordered-by system;
            uses TapiModule-TypeDefinitions:G_Tapi_NameAndValue;
            min-elements 1;
        }
        list label {
            description "List of labels.A property of an entity with a value that is not expected to be unique and is allowed to change. A label carries no semantics with respect to the purpose of the entity and has no effect on the entity behavior or state.";
            key 'valueName';
            config true;
            ordered-by system;
            uses TapiModule-TypeDefinitions:G_Tapi_NameAndValue;
        }
        list extension {
            description "List of simple name-value extentions. Extension provides an opportunity to define properties not declared in the class that extend the class enabling a realization with simple ad-hoc extension of standard classes to be conformant.";
            key 'valueName';
            config true;
            ordered-by system;
            uses TapiModule-TypeDefinitions:G_Tapi_NameAndValue;
        }
        leaf layerProtocolName {
            type TapiModule-TypeDefinitions:Tapi_LayerProtocolName;
        }
        leaf direction {
            type TapiModule-TypeDefinitions:Tapi_ForwardingDirection;
        }
        leaf administrativeState {
            type TapiModule-TypeDefinitions:Tapi_AdministrativeState;
        }
        leaf operationalState {
            type TapiModule-TypeDefinitions:Tapi_OperationalState;
        }
        leaf lifecycleState {
            type TapiModule-TypeDefinitions:Tapi_LifecycleState;
        }
    }
    grouping G_Tapi_Connection {
        list _connectionPort {
            key 'localId';
            config true;
            ordered-by system;
            uses G_Tapi_ConnectionPort;
            min-elements 2;
        }
        list _path {
            key 'localId';
            config true;
            ordered-by system;
            uses G_Tapi_Route;
        }
        leaf _node {
            type leafref {
                path '/Tapi_Topology/_node/uuid';
            }
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            key 'valueName';
            config true;
            ordered-by system;
            uses TapiModule-TypeDefinitions:G_Tapi_NameAndValue;
            min-elements 1;
        }
        list label {
            description "List of labels.A property of an entity with a value that is not expected to be unique and is allowed to change. A label carries no semantics with respect to the purpose of the entity and has no effect on the entity behavior or state.";
            key 'valueName';
            config true;
            ordered-by system;
            uses TapiModule-TypeDefinitions:G_Tapi_NameAndValue;
        }
        list extension {
            description "List of simple name-value extentions. Extension provides an opportunity to define properties not declared in the class that extend the class enabling a realization with simple ad-hoc extension of standard classes to be conformant.";
            key 'valueName';
            config true;
            ordered-by system;
            uses TapiModule-TypeDefinitions:G_Tapi_NameAndValue;
        }
        leaf layerProtocolName {
            type TapiModule-TypeDefinitions:Tapi_LayerProtocolName;
        }
        leaf direction {
            type TapiModule-TypeDefinitions:Tapi_ForwardingDirection;
        }
        leaf operationalState {
            type TapiModule-TypeDefinitions:Tapi_OperationalState;
        }
        leaf lifecycleState {
            type TapiModule-TypeDefinitions:Tapi_LifecycleState;
        }
    }
    grouping G_Tapi_Route {
        uses G_Tapi_LocalComponent;
        leaf-list _lowerConnection {
            ordered-by system;
            type leafref {
                path '/Tapi_ConnectivityService/_connection/uuid';
            }
            min-elements 1;
        }
    }
    grouping G_Tapi_LinkPort {
        uses G_Tapi_LocalComponent;
        leaf _nodeEdgePoint {
            type leafref {
                path '/Tapi_Topology/_node/_ownedNodeEdgePoint/uuid';
            }
        }
        leaf role {
            type TapiModule-TypeDefinitions:Tapi_PortRole;
            description "Each LinkEnd of the Link has a role (e.g., symmetric, hub, spoke, leaf, root)  in the context of the Link with respect to the Link function. ";
        }
        leaf direction {
            type TapiModule-TypeDefinitions:Tapi_PortDirection;
            description "The orientation of defined flow at the LinkEnd.";
        }
    }
    grouping G_Tapi_ServicePort {
        uses G_Tapi_LocalComponent;
        leaf _serviceEndPoint {
            type leafref {
                path '/Tapi_ServiceEndPoint/uuid';
            }
        }
        leaf role {
            type TapiModule-TypeDefinitions:Tapi_PortRole;
            description "Each EP of the FC has a role (e.g., working, protection, protected, symmetric, hub, spoke, leaf, root)  in the context of the FC with respect to the FC function. ";
        }
        leaf direction {
            type TapiModule-TypeDefinitions:Tapi_PortDirection;
            description "The orientation of defined flow at the EndPoint.";
        }
        leaf serviceLayer {
            type TapiModule-TypeDefinitions:Tapi_LayerProtocolName;
        }
    }
    grouping G_Tapi_ConnectionPort {
        uses G_Tapi_LocalComponent;
        leaf _connectionEndPoint {
            type leafref {
                path '/Tapi_ConnectionEndPoint/uuid';
            }
        }
        leaf role {
            type TapiModule-TypeDefinitions:Tapi_PortRole;
            description "Each EP of the FC has a role (e.g., working, protection, protected, symmetric, hub, spoke, leaf, root)  in the context of the FC with respect to the FC function. ";
        }
        leaf direction {
            type TapiModule-TypeDefinitions:Tapi_PortDirection;
            description "The orientation of defined flow at the EndPoint.";
        }
    }
    grouping G_Tapi_LayerProtocol {
        uses G_Tapi_LocalComponent;
        leaf _lpSpec {
            type string;
            description "The LpSpec identifies the interna structure of the LP explaining internal flexibilities, degree of termination and degree of adaptation on both client and server side.";
        }
        leaf layerProtocolName {
            type TapiModule-TypeDefinitions:Tapi_LayerProtocolName;
            description "Indicate the specific layer-protocol described by the LayerProtocol entity.";
        }
        leaf terminationDirection {
            type TapiModule-TypeDefinitions:Tapi_TerminationDirection;
            description "The overall directionality of the LP. 
                - A BIDIRECTIONAL LP will have some SINK and/or SOURCE flowss.
                - A SINK LP can only contain elements with SINK flows or CONTRA_DIRECTION_SOURCE flows
                - A SOURCE LP can only contain SOURCE flows or CONTRA_DIRECTION_SINK flows";
        }
        leaf terminationState {
            type TapiModule-TypeDefinitions:Tapi_TerminationState;
            description "Indicates whether the layer is terminated and if so how.";
        }
    }
    grouping G_Tapi_TransferCostPac {
        list costCharacteristic {
            description "The list of costs where each cost relates to some aspect of the TopologicalEntity.";
            key 'costAlgorithm';
            config true;
            ordered-by system;
            uses TapiModule-TypeDefinitions:G_Tapi_CostCharacteristic;
            min-elements 1;
        }
    }
    grouping G_Tapi_RiskParameterPac {
        list riskCharacteristic {
            description "A list of risk characteristics for consideration in an analysis of shared risk. Each element of the list represents a specific risk consideration.";
            key 'riskCharacteristicName';
            config true;
            ordered-by system;
            uses TapiModule-TypeDefinitions:G_Tapi_RiskCharacteristic;
            min-elements 1;
        }
    }
    grouping G_Tapi_LayerProtocolTransitionPac {
        leaf-list transitionedLayerProtocolName {
            description "Provides the ordered structure of layer protocol transitions encapsulated in the TopologicalEntity. The ordering relates to the LinkPort role.";
            ordered-by system;
            type string;
            min-elements 1;
        }
        leaf-list _nodeEdgePoint {
            description "Lists the LTPs that define the layer protocol transition of the transitional link.";
            ordered-by system;
            type leafref {
                path '/Tapi_Topology/_node/_ownedNodeEdgePoint/uuid';
            }
            min-elements 1;
        }
    }
    grouping G_Tapi_TransferTimingPac {
        leaf fixedLatencyCharacteristic {
            type string;
            description "A TopologicalEntity suffers delay caused by the realization of the servers (e.g. distance related; FEC encoding etc.) along with some client specific processing. This is the total average latency effect of the TopologicalEntity";
        }
        leaf jitterCharacteristic {
            type string;
            description "High frequency deviation from true periodicity of a signal and therefore a small high rate of change of transfer latency.
                Applies to TDM systems (and not packet).";
        }
        leaf wanderCharacteristic {
            type string;
            description "Low frequency deviation from true periodicity of a signal and therefore a small low rate of change of transfer latency.
                Applies to TDM systems (and not packet).";
        }
        leaf-list queuingLatency {
            description "The effect on the latency of a queuing process. This only has significant effect for packet based systems and has a complex characteristic.";
            ordered-by system;
            type string;
        }
    }
    grouping G_Tapi_TransferIntegrityPac {
        leaf errorCharacteristic {
            type string;
            description "Describes the degree to which the signal propagated can be errored. 
                Applies to TDM systems as the errored signal will be propagated and not packet as errored packets will be discarded.";
        }
        leaf lossCharacteristic {
            type string;
            description "Describes the acceptable characteristic of lost packets where loss may result from discard due to errors or overflow.
                Applies to packet systems and not TDM (as for TDM errored signals are propagated unless grossly errored and overflow/underflow turns into timing slips).";
        }
        leaf repeatDeliveryCharacteristic {
            type string;
            description "Primarily applies to packet systems where a packet may be delivered more than once (in fault recovery for example). 
                It can also apply to TDM where several frames may be received twice due to switching in a system with a large differential propagation delay.";
        }
        leaf deliveryOrderCharacteristic {
            type string;
            description "Describes the degree to which packets will be delivered out of sequence.
                Does not apply to TDM as the TDM protocols maintain strict order.";
        }
        leaf unavailableTimeCharacteristic {
            type string;
            description "Describes the duration for which there may be no valid signal propagated.";
        }
        leaf serverIntegrityProcessCharacteristic {
            type string;
            description "Describes the effect of any server integrity enhancement process on the characteristics of the TopologicalEntity.";
        }
    }
    grouping G_Tapi_TransferCapacityPac {
        container totalPotentialCapacity {
            description "An optimistic view of the capacity of the TopologicalEntity assuming that any shared capacity is available to be taken.";
            config true;
            uses TapiModule-TypeDefinitions:G_Tapi_Capacity;
        }
        container availableCapacity {
            description "Capacity available to be assigned.";
            config true;
            uses TapiModule-TypeDefinitions:G_Tapi_Capacity;
        }
        list capacityAssignedToUserView {
            description "Capacity already assigned";
            key 'numberingRange';
            config true;
            ordered-by system;
            uses TapiModule-TypeDefinitions:G_Tapi_Capacity;
        }
        leaf capacityInteractionAlgorithm {
            type string;
            description "A reference to an algorithm that describes how various chunks of allocated capacity interact (e.g. when shared)";
        }
    }
    grouping G_Tapi_ValidationPac {
        list validationMechanism {
            description "Provides details of the specific validation mechanism(s) used to confirm the presence of an intended topologicalEntity.";
            key 'validationRobustness';
            config true;
            ordered-by system;
            uses TapiModule-TypeDefinitions:G_Tapi_ValidationMechanism;
            min-elements 1;
        }
    }
    grouping G_Tapi_TeLink {
        uses G_Tapi_LocalComponent;
        leaf-list _node {
            ordered-by system;
            type leafref {
                path '/Tapi_Topology/_node/uuid';
            }
            max-elements 2;
            min-elements 2;
        }
        leaf-list _linkPort {
            ordered-by system;
            type leafref {
                path '/Tapi_Topology/_link/_linkPort/localId';
            }
            max-elements 2;
        }
        leaf _link {
            type leafref {
                path '/Tapi_Topology/_link/uuid';
            }
        }
    }
    list Tapi_Path {
        key 'uuid';
        config true;
        ordered-by system;
        uses G_Tapi_Path;
    }
    grouping G_Tapi_Path {
        list _telink {
            key 'localId';
            config true;
            ordered-by system;
            uses G_Tapi_TeLink;
            min-elements 1;
        }
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        container routingConstraint {
            config true;
            uses G_Tapi_ConnectivityConstraint;
        }
    }
    grouping G_Tapi_ConnectivityConstraint {
        leaf serviceType {
            type TapiModule-TypeDefinitions:Tapi_ServiceType;
        }
        container requestedCapacity {
            config true;
            uses TapiModule-TypeDefinitions:G_Tapi_Capacity;
        }
        leaf serviceLevel {
            type string;
            description "An abstract value the meaning of which is mutually agreed – typically represents metrics such as - Class of service, priority, resiliency, availability";
        }
        leaf-list serviceLayer {
            ordered-by system;
            type TapiModule-TypeDefinitions:Tapi_LayerProtocolName;
        }
        list costCharacteristic {
            description "The list of costs where each cost relates to some aspect of the TopologicalEntity.";
            key 'costAlgorithm';
            config true;
            ordered-by system;
            uses TapiModule-TypeDefinitions:G_Tapi_CostCharacteristic;
        }
        list riskCharacteristic {
            description "A list of risk characteristics for consideration in an analysis of shared risk. Each element of the list represents a specific risk consideration.";
            key 'riskCharacteristicName';
            config true;
            ordered-by system;
            uses TapiModule-TypeDefinitions:G_Tapi_RiskCharacteristic;
        }
        list latencyCharacteristic {
            description "The effect on the latency of a queuing process. This only has significant effect for packet based systems and has a complex characteristic.";
            key 'latencyValue';
            config true;
            ordered-by system;
            uses TapiModule-TypeDefinitions:G_Tapi_QueuingLatency;
        }
        leaf-list includePath {
            ordered-by system;
            type leafref {
                path '/Tapi_Path/uuid';
            }
        }
        leaf-list excludePath {
            ordered-by system;
            type leafref {
                path '/Tapi_Path/uuid';
            }
        }
    }
    grouping G_Tapi_ScheduleInfo {
        leaf startTime {
            type string;
        }
        leaf endTime {
            type string;
        }
    }
    grouping G_Tapi_PathOptimizationConstraint {
        leaf trafficInterruption {
            type TapiModule-TypeDefinitions:Tapi_DirectiveValue;
        }
    }
    grouping G_Tapi_PathObjectiveFunction {
        leaf concurrentPaths {
            type TapiModule-TypeDefinitions:Tapi_DirectiveValue;
        }
        leaf bandwidthOptimization {
            type TapiModule-TypeDefinitions:Tapi_DirectiveValue;
        }
        leaf costOptimization {
            type TapiModule-TypeDefinitions:Tapi_DirectiveValue;
        }
        leaf linkUtilization {
            type TapiModule-TypeDefinitions:Tapi_DirectiveValue;
        }
        leaf resourceSharing {
            type TapiModule-TypeDefinitions:Tapi_DirectiveValue;
        }
    }
    grouping G_Tapi_GlobalComponent {
        leaf uuid {
            type TapiModule-TypeDefinitions:Tapi_UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            key 'valueName';
            config true;
            ordered-by system;
            uses TapiModule-TypeDefinitions:G_Tapi_NameAndValue;
            min-elements 1;
        }
        list label {
            description "List of labels.A property of an entity with a value that is not expected to be unique and is allowed to change. A label carries no semantics with respect to the purpose of the entity and has no effect on the entity behavior or state.";
            key 'valueName';
            config true;
            ordered-by system;
            uses TapiModule-TypeDefinitions:G_Tapi_NameAndValue;
        }
        list extension {
            description "List of simple name-value extentions. Extension provides an opportunity to define properties not declared in the class that extend the class enabling a realization with simple ad-hoc extension of standard classes to be conformant.";
            key 'valueName';
            config true;
            ordered-by system;
            uses TapiModule-TypeDefinitions:G_Tapi_NameAndValue;
        }
    }
    grouping G_Tapi_LocalComponent {
        leaf localId {
            type string;
        }
    }
}
