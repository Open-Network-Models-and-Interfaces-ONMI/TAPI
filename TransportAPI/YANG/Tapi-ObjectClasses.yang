module Tapi-ObjectClasses {
    namespace "uri:onf:Tapi-ObjectClasses";
    prefix Tapi-ObjectClasses;
    import Tapi-TypeDefinitions {
        prefix Tapi-TypeDefinitions;
    }
    import TapiSpec-ObjectClasses {
        prefix TapiSpec-ObjectClasses;
    }
    revision 2016-05-22{}
    grouping Topology {
        uses GlobalClass;
        list _node {
        	config false;
            ordered-by system;
            uses Node;
        }
        list _link {
        	config false;
            ordered-by system;
            uses Link;
        }
        leaf-list layerProtocolName {
            ordered-by system;
            type Tapi-TypeDefinitions:LayerProtocolName;
            min-elements 1;
        }
    }
    container Context {
        config true;
        uses GlobalClass;
        list _serviceEndPoint {
        	config false;
        	ordered-by system;
            uses ServiceEndPoint;
            min-elements 2;
        }
        list _connectivityService {
            key 'uuid';
            config true;
            ordered-by system;
            uses ConnectivityService;
        }
        list _vnwService {
            key 'uuid';
            config true;
            ordered-by system;
            uses VirtualNetworkService;
        }
        list _topology {
        	config false;
            ordered-by system;
            uses Topology;
        }
        list _path {
        	config false;
        	ordered-by system;
            uses Path;
        }
    }
    grouping Node {
        uses GlobalClass;
        list _ownedNodeEdgePoint {
        	config false;
            ordered-by system;
            uses NodeEdgePoint;
        }
        leaf-list _aggregatedNodeEdgePoint {
            ordered-by system;
            type leafref {
                path '/Context/_topology/_node/_ownedNodeEdgePoint/uuid';
            }
            config false;
        }
        leaf _encapTopology {
            type leafref {
                path '/Context/_topology/uuid';
            }
            config false;
        }
        container _state {
            uses AdminStatePac;
        }
        container _transferCapacity {
            uses TransferCapacityPac;
        }
        container _transferCost {
            uses TransferCostPac;
        }
        container _transferIntegrity {
            uses TransferIntegrityPac;
        }
        container _transferTiming {
            uses TransferTimingPac;
        }
        leaf-list layerProtocolName {
            ordered-by system;
            type Tapi-TypeDefinitions:LayerProtocolName;
            config false;
            min-elements 1;
        }
    }
    grouping Link {
        uses GlobalClass;
        list _linkPort {
        	config false;
            ordered-by system;
            uses LinkPort;
            min-elements 2;
        }
        leaf-list _node {
            ordered-by system;
            type leafref {
                path '/Context/_topology/_node/uuid';
            }
            config false;
            min-elements 2;
        }
        container _state {
            uses AdminStatePac;
        }
        container _transferCapacity {
            uses TransferCapacityPac;
        }
        container _transferCost {
            uses TransferCostPac;
        }
        container _transferIntegrity {
            uses TransferIntegrityPac;
        }
        container _transferTiming {
            uses TransferTimingPac;
        }
        container _riskParameter {
            uses RiskParameterPac;
        }
        container _validation {
            uses ValidationPac;
        }
        container _lpTransition {
            uses LayerProtocolTransitionPac;
        }
        leaf-list layerProtocolName {
            ordered-by system;
            type Tapi-TypeDefinitions:LayerProtocolName;
            config false;
            min-elements 1;
        }
        leaf direction {
            type Tapi-TypeDefinitions:ForwardingDirection;
            config false;
            description "The directionality of the Link. 
                Is applicable to simple Links where all LinkEnds are BIDIRECTIONAL (the Link will be BIDIRECTIONAL) or UNIDIRECTIONAL (the Link will be UNIDIRECTIONAL). 
                Is not present in more complex cases.";
        }
    }
    grouping NodeEdgePoint {
        uses GlobalClass;
        container _ltpSpecData {
            uses TapiSpec-ObjectClasses:LtpSpec;
        }
        list _layerProtocol {
        	config false;
            ordered-by system;
            uses LayerProtocol;
            min-elements 1;
        }
        leaf-list _clientNodeEdgePoint {
            ordered-by system;
            type leafref {
                path '/Context/_topology/_node/_ownedNodeEdgePoint/uuid';
            }
            config false;
        }
        container _state {
            uses AdminStatePac;
        }
        leaf direction {
            type Tapi-TypeDefinitions:TerminationDirection;
            config false;
        }
    }
    grouping ServiceEndPoint {
        uses GlobalClass;
        container _ltpSpecData {
            uses TapiSpec-ObjectClasses:LtpSpec;
        }
        list _layerProtocol {
        	config false;
            ordered-by system;
            uses LayerProtocol;
            min-elements 1;
        }
        leaf-list _mappedNodeEdgePoint {
            ordered-by system;
            type leafref {
                path '/Context/_topology/_node/_ownedNodeEdgePoint/uuid';
            }
            config false;
        }
        list _connectionEndPoint {
        	config false;
            ordered-by system;
            uses ConnectionEndPoint;
        }
        container _state {
            uses LifecycleStatePac;
        }
        leaf direction {
            type Tapi-TypeDefinitions:TerminationDirection;
            config false;
        }
    }
    grouping ConnectionEndPoint {
        uses GlobalClass;
        container _ltpSpecData {
            uses TapiSpec-ObjectClasses:LtpSpec;
        }
        list _layerProtocol {
        	config false;
            ordered-by system;
            uses LayerProtocol;
            min-elements 1;
        }
        leaf-list _clientNodeEdgePoint {
            ordered-by system;
            type leafref {
                path '/Context/_topology/_node/_ownedNodeEdgePoint/uuid';
            }
            config false;
        }
        leaf _serverNodeEdgePoint {
            type leafref {
                path '/Context/_topology/_node/_ownedNodeEdgePoint/uuid';
            }
            config false;
        }
        leaf _peerConnectionEndPoint {
            type leafref {
                path '/Context/_serviceEndPoint/_connectionEndPoint/uuid';
            }
            config false;
        }
        container _state {
            uses OperationalStatePac;
        }
        leaf direction {
            type Tapi-TypeDefinitions:TerminationDirection;
            config false;
        }
    }
    grouping ConnectivityService {
        uses GlobalClass;
        list _connection {
        	config false;
            ordered-by system;
            uses Connection;
        }
        list _servicePort {
            key 'localId';
            config true;
            ordered-by system;
            uses ConnectivityServicePort;
            min-elements 2;
        }
        container _connConstraints {
            config true;
            uses ConnectivityConstraint;
        }
        container _schedule {
            config true;
            uses ScheduleInfo;
        }
        container _state {
            config true;
            uses AdminStatePac;
        }
        leaf layerProtocolName {
            type Tapi-TypeDefinitions:LayerProtocolName;
        }
        leaf direction {
            type Tapi-TypeDefinitions:ForwardingDirection;
        }
    }
    grouping Connection {
        uses GlobalClass;
        list _connectionPort {
        	config false;
            ordered-by system;
            uses ConnectionPort;
            min-elements 2;
        }
        list _route {
        	config false;
            ordered-by system;
            uses Route;
        }
        leaf _node {
            type leafref {
                path '/Context/_topology/_node/uuid';
            }
            config false;
        }
        container _state {
            uses OperationalStatePac;
        }
        leaf layerProtocolName {
            type Tapi-TypeDefinitions:LayerProtocolName;
            config false;
        }
        leaf direction {
            type Tapi-TypeDefinitions:ForwardingDirection;
            config false;
        }
    }
    grouping Route {
        uses LocalClass;
        leaf-list _lowerConnection {
            ordered-by system;
            type leafref {
                path '/Context/_connectivityService/_connection/uuid';
            }
            config false;
            min-elements 1;
        }
    }
    grouping LinkPort {
        uses LocalClass;
        leaf _nodeEdgePoint {
            type leafref {
                path '/Context/_topology/_node/_ownedNodeEdgePoint/uuid';
            }
            config false;
        }
        leaf role {
            type Tapi-TypeDefinitions:PortRole;
            config false;
            description "Each LinkEnd of the Link has a role (e.g., symmetric, hub, spoke, leaf, root)  in the context of the Link with respect to the Link function. ";
        }
        leaf direction {
            type Tapi-TypeDefinitions:PortDirection;
            config false;
            description "The orientation of defined flow at the LinkEnd.";
        }
    }
    grouping ConnectivityServicePort {
        uses LocalClass;
        leaf _serviceEndPoint {
            type leafref {
                path '/Context/_serviceEndPoint/uuid';
            }
            config false;
        }
        leaf role {
            type Tapi-TypeDefinitions:PortRole;
            config false;
            description "Each EP of the FC has a role (e.g., working, protection, protected, symmetric, hub, spoke, leaf, root)  in the context of the FC with respect to the FC function. ";
        }
        leaf direction {
            type Tapi-TypeDefinitions:PortDirection;
            config false;
            description "The orientation of defined flow at the EndPoint.";
        }
        leaf serviceLayer {
            type Tapi-TypeDefinitions:LayerProtocolName;
            config false;
        }
    }
    grouping ConnectionPort {
        uses LocalClass;
        leaf _connectionEndPoint {
            type leafref {
                path '/Context/_serviceEndPoint/_connectionEndPoint/uuid';
            }
            config false;
        }
        leaf role {
            type Tapi-TypeDefinitions:PortRole;
            config false;
            description "Each EP of the FC has a role (e.g., working, protection, protected, symmetric, hub, spoke, leaf, root)  in the context of the FC with respect to the FC function. ";
        }
        leaf direction {
            type Tapi-TypeDefinitions:PortDirection;
            config false;
            description "The orientation of defined flow at the EndPoint.";
        }
    }
    grouping LayerProtocol {
        uses LocalClass;
        container _lpSpecData {
            uses TapiSpec-ObjectClasses:LpSpec;
        }
        leaf layerProtocolName {
            type Tapi-TypeDefinitions:LayerProtocolName;
            description "Indicate the specific layer-protocol described by the LayerProtocol entity.";
        }
        leaf terminationDirection {
            type Tapi-TypeDefinitions:TerminationDirection;
            description "The overall directionality of the LP. 
                - A BIDIRECTIONAL LP will have some SINK and/or SOURCE flowss.
                - A SINK LP can only contain elements with SINK flows or CONTRA_DIRECTION_SOURCE flows
                - A SOURCE LP can only contain SOURCE flows or CONTRA_DIRECTION_SINK flows";
        }
        leaf terminationState {
            type Tapi-TypeDefinitions:TerminationState;
            description "Indicates whether the layer is terminated and if so how.";
        }
    }
    grouping TransferCostPac {
        list costCharacteristic {
        	config false;
            description "The list of costs where each cost relates to some aspect of the TopologicalEntity.";
            ordered-by system;
            uses Tapi-TypeDefinitions:CostCharacteristic;
            min-elements 1;
        }
    }
    grouping RiskParameterPac {
        list riskCharacteristic {
        	config false;
            description "A list of risk characteristics for consideration in an analysis of shared risk. Each element of the list represents a specific risk consideration.";
            ordered-by system;
            uses Tapi-TypeDefinitions:RiskCharacteristic;
            min-elements 1;
        }
    }
    grouping LayerProtocolTransitionPac {
        leaf-list transitionedLayerProtocolName {
            description "Provides the ordered structure of layer protocol transitions encapsulated in the TopologicalEntity. The ordering relates to the LinkPort role.";
            ordered-by system;
            type string;
            min-elements 1;
        }
        leaf-list _nodeEdgePoint {
            description "Lists the LTPs that define the layer protocol transition of the transitional link.";
            ordered-by system;
            type leafref {
                path '/Context/_topology/_node/_ownedNodeEdgePoint/uuid';
            }
            min-elements 1;
        }
    }
    grouping TransferTimingPac {
        leaf fixedLatencyCharacteristic {
            type string;
            config false;
            description "A TopologicalEntity suffers delay caused by the realization of the servers (e.g. distance related; FEC encoding etc.) along with some client specific processing. This is the total average latency effect of the TopologicalEntity";
        }
        leaf jitterCharacteristic {
            type string;
            config false;
            description "High frequency deviation from true periodicity of a signal and therefore a small high rate of change of transfer latency.
                Applies to TDM systems (and not packet).";
        }
        leaf wanderCharacteristic {
            type string;
            config false;
            description "Low frequency deviation from true periodicity of a signal and therefore a small low rate of change of transfer latency.
                Applies to TDM systems (and not packet).";
        }
        list queuingLatency {
        	config false;
            description "The effect on the latency of a queuing process. This only has significant effect for packet based systems and has a complex characteristic.";
            ordered-by system;
            uses Tapi-TypeDefinitions:QueuingLatency;
        }
    }
    grouping TransferIntegrityPac {
        leaf errorCharacteristic {
            type string;
            config false;
            description "Describes the degree to which the signal propagated can be errored. 
                Applies to TDM systems as the errored signal will be propagated and not packet as errored packets will be discarded.";
        }
        leaf lossCharacteristic {
            type string;
            config false;
            description "Describes the acceptable characteristic of lost packets where loss may result from discard due to errors or overflow.
                Applies to packet systems and not TDM (as for TDM errored signals are propagated unless grossly errored and overflow/underflow turns into timing slips).";
        }
        leaf repeatDeliveryCharacteristic {
            type string;
            config false;
            description "Primarily applies to packet systems where a packet may be delivered more than once (in fault recovery for example). 
                It can also apply to TDM where several frames may be received twice due to switching in a system with a large differential propagation delay.";
        }
        leaf deliveryOrderCharacteristic {
            type string;
            config false;
            description "Describes the degree to which packets will be delivered out of sequence.
                Does not apply to TDM as the TDM protocols maintain strict order.";
        }
        leaf unavailableTimeCharacteristic {
            type string;
            config false;
            description "Describes the duration for which there may be no valid signal propagated.";
        }
        leaf serverIntegrityProcessCharacteristic {
            type string;
            config false;
            description "Describes the effect of any server integrity enhancement process on the characteristics of the TopologicalEntity.";
        }
    }
    grouping TransferCapacityPac {
        container totalPotentialCapacity {
            description "An optimistic view of the capacity of the TopologicalEntity assuming that any shared capacity is available to be taken.";
            uses Tapi-TypeDefinitions:Capacity;
        }
        container availableCapacity {
            description "Capacity available to be assigned.";
            uses Tapi-TypeDefinitions:Capacity;
        }
        list capacityAssignedToUserView {
        	config false;
            description "Capacity already assigned";
            ordered-by system;
            uses Tapi-TypeDefinitions:Capacity;
        }
        leaf capacityInteractionAlgorithm {
            type string;
            config false;
            description "A reference to an algorithm that describes how various chunks of allocated capacity interact (e.g. when shared)";
        }
    }
    grouping ValidationPac {
        list validationMechanism {
        	config false;
            description "Provides details of the specific validation mechanism(s) used to confirm the presence of an intended topologicalEntity.";
            ordered-by system;
            uses Tapi-TypeDefinitions:ValidationMechanism;
            min-elements 1;
        }
    }
    grouping TeLink {
        uses LocalClass;
        leaf-list _node {
            ordered-by system;
            type leafref {
                path '/Context/_topology/_node/uuid';
            }
            config false;
            max-elements 2;
            min-elements 2;
        }
        leaf-list _nodeEdgePoint {
            ordered-by system;
            type leafref {
                path '/Context/_topology/_node/_ownedNodeEdgePoint/uuid';
            }
            config false;
            max-elements 2;
        }
    }
    grouping Path {
        uses GlobalClass;
        list _telink {
            config false;
            ordered-by system;
            uses TeLink;
            min-elements 1;
        }
        container _routingConstraint {
            uses ConnectivityConstraint;
        }
        container _optimizationConstraint {
            uses PathOptimizationConstraint;
        }
        container _objectiveFunction {
            uses PathObjectiveFunction;
        }
    }
    grouping GlobalClass {
        leaf uuid {
            type Tapi-TypeDefinitions:UniversalId;
            description "UUID: An identifier that is universally unique
                (consider in the context of Identifier: A property of an entity/role with a value that is unique within an identifier space, where the identifier space is itself globally unique, and immutable. An identifier carries no semantics with respect to the purpose or state of the entity)";
        }
        list name {
            description "List of names. A property of an entity with a value that is unique in some namespace but may change during the life of the entity. A name carries no semantics with respect to the purpose of the entity.";
            key 'valueName';
            config false;
            ordered-by system;
            uses Tapi-TypeDefinitions:NameAndValue;
            min-elements 1;
        }
        list label {
            description "List of labels.A property of an entity with a value that is not expected to be unique and is allowed to change. A label carries no semantics with respect to the purpose of the entity and has no effect on the entity behavior or state.";
            key 'valueName';
            config false;
            ordered-by system;
            uses Tapi-TypeDefinitions:NameAndValue;
        }
        list extension {
            description "List of simple name-value extentions. Extension provides an opportunity to define properties not declared in the class that extend the class enabling a realization with simple ad-hoc extension of standard classes to be conformant.";
            key 'valueName';
            config false;
            ordered-by system;
            uses Tapi-TypeDefinitions:NameAndValue;
        }
    }
    grouping LocalClass {
        leaf localId {
            type string;
        }
    }
    grouping AdminStatePac {
        leaf administrativeState {
            type Tapi-TypeDefinitions:AdministrativeState;
        }
        leaf operationalState {
            type Tapi-TypeDefinitions:OperationalState;
        }
        leaf lifecycleState {
            type Tapi-TypeDefinitions:LifecycleState;
        }
    }
    grouping LifecycleStatePac {
        leaf lifecycleState {
            type Tapi-TypeDefinitions:LifecycleState;
        }
    }
    grouping OperationalStatePac {
        leaf operationalState {
            type Tapi-TypeDefinitions:OperationalState;
        }
        leaf lifecycleState {
            type Tapi-TypeDefinitions:LifecycleState;
        }
    }
    grouping ConnectivityConstraint {
        leaf serviceType {
            type Tapi-TypeDefinitions:ServiceType;
            config false;
        }
        leaf serviceLevel {
            type string;
            config false;
            description "An abstract value the meaning of which is mutually agreed – typically represents metrics such as - Class of service, priority, resiliency, availability";
        }
        leaf-list serviceLayer {
            ordered-by system;
            type Tapi-TypeDefinitions:LayerProtocolName;
            config false;
        }
        container requestedCapacity {
            uses Tapi-TypeDefinitions:Capacity;
        }
        list costCharacteristic {
            description "The list of costs where each cost relates to some aspect of the TopologicalEntity.";
            config false;
            ordered-by system;
            uses Tapi-TypeDefinitions:CostCharacteristic;
        }
        list riskCharacteristic {
            description "A list of risk characteristics for consideration in an analysis of shared risk. Each element of the list represents a specific risk consideration.";
            config false;
            ordered-by system;
            uses Tapi-TypeDefinitions:RiskCharacteristic;
        }
        list latencyCharacteristic {
            description "The effect on the latency of a queuing process. This only has significant effect for packet based systems and has a complex characteristic.";
            config false;
            ordered-by system;
            uses Tapi-TypeDefinitions:QueuingLatency;
        }
        leaf-list includeTopology {
            ordered-by system;
            type leafref {
                path '/Context/_topology/uuid';
            }
            config false;
        }
        leaf-list avoidTopology {
            ordered-by system;
            type leafref {
                path '/Context/_topology/uuid';
            }
            config false;
        }
        leaf-list includePath {
            ordered-by system;
            type leafref {
                path '/Context/_path/uuid';
            }
            config false;
        }
        leaf-list excludePath {
            ordered-by system;
            type leafref {
                path '/Context/_path/uuid';
            }
            config false;
        }
    }
    grouping PathOptimizationConstraint {
        leaf trafficInterruption {
            type Tapi-TypeDefinitions:DirectiveValue;
            config false;
        }
    }
    grouping PathObjectiveFunction {
        leaf bandwidthOptimization {
            type Tapi-TypeDefinitions:DirectiveValue;
            config false;
        }
        leaf concurrentPaths {
            type Tapi-TypeDefinitions:DirectiveValue;
            config false;
        }
        leaf costOptimization {
            type Tapi-TypeDefinitions:DirectiveValue;
            config false;
        }
        leaf linkUtilization {
            type Tapi-TypeDefinitions:DirectiveValue;
            config false;
        }
        leaf resourceSharing {
            type Tapi-TypeDefinitions:DirectiveValue;
            config false;
        }
    }
    grouping ScheduleInfo {
        leaf endTime {
            type Tapi-TypeDefinitions:DateAndTime;
        }
        leaf startTime {
            type Tapi-TypeDefinitions:DateAndTime;
        }
    }
    grouping VirtualNetworkService {
        uses GlobalClass;
        leaf _topology {
            type leafref {
                path '/Context/_topology/uuid';
            }
            config false;
        }
        list _servicePort {
            key 'localId';
            config true;
            ordered-by system;
            uses VirtualNetworkServicePort;
            min-elements 2;
        }
        container _vnwConstraint {
            config true;
            uses VirtualNetworkConstraint;
        }
        container _schedule {
            config true;
            uses ScheduleInfo;
        }
        container _state {
            config true;
            uses AdminStatePac;
        }
        leaf-list layerProtocolName {
            ordered-by system;
            type Tapi-TypeDefinitions:LayerProtocolName;
            min-elements 1;
        }
    }
    grouping VirtualNetworkServicePort {
        uses LocalClass;
        leaf _serviceEndPoint {
            type leafref {
                path '/Context/_serviceEndPoint/uuid';
            }
            config false;
        }
        leaf role {
            type Tapi-TypeDefinitions:PortRole;
            config false;
            description "Each EP of the FC has a role (e.g., working, protection, protected, symmetric, hub, spoke, leaf, root)  in the context of the FC with respect to the FC function. ";
        }
        leaf direction {
            type Tapi-TypeDefinitions:PortDirection;
            config false;
            description "The orientation of defined flow at the EndPoint.";
        }
        leaf serviceLayer {
            type Tapi-TypeDefinitions:LayerProtocolName;
            config false;
        }
    }
    grouping VirtualNetworkConstraint {
        leaf serviceType {
            type Tapi-TypeDefinitions:ServiceType;
        }
        leaf serviceLevel {
            type string;
            description "An abstract value the meaning of which is mutually agreed – typically represents metrics such as - Class of service, priority, resiliency, availability";
        }
        leaf-list serviceLayer {
            ordered-by system;
            type Tapi-TypeDefinitions:LayerProtocolName;
        }
        container requestedCapacity {
            config true;
            uses Tapi-TypeDefinitions:Capacity;
        }
        list costCharacteristic {
            description "The list of costs where each cost relates to some aspect of the TopologicalEntity.";
            key 'costAlgorithm';
            config true;
            ordered-by system;
            uses Tapi-TypeDefinitions:CostCharacteristic;
        }
        list riskCharacteristic {
            description "A list of risk characteristics for consideration in an analysis of shared risk. Each element of the list represents a specific risk consideration.";
            key 'riskCharacteristicName';
            config true;
            ordered-by system;
            uses Tapi-TypeDefinitions:RiskCharacteristic;
        }
        list latencyCharacteristic {
            description "The effect on the latency of a queuing process. This only has significant effect for packet based systems and has a complex characteristic.";
            key 'latencyValue';
            config true;
            ordered-by system;
            uses Tapi-TypeDefinitions:QueuingLatency;
        }
    }
}
