module TapiModule-ObjectClasses-ConnectivityPac {
    namespace "uri:onf:TapiModule-ObjectClasses-ConnectivityPac";
    prefix TapiModule-ObjectClasses-ConnectivityPac;
    import TapiModule-TypeDefinitions {
        prefix TapiModule-TypeDefinitions;
    }
    revision 2016-03-10{}
    grouping G_Tapi_ScheduleInfo {
        leaf startTime {
            type string;
        }
        leaf endTime {
            type string;
        }
    }
    grouping G_Tapi_PathOptimizationConstraint {
        leaf trafficInterruption {
            type TapiModule-TypeDefinitions:Tapi_DirectiveValue;
        }
    }
    grouping G_Tapi_PathObjectiveFunction {
        leaf concurrentPaths {
            type TapiModule-TypeDefinitions:Tapi_DirectiveValue;
        }
        leaf bandwidthOptimization {
            type TapiModule-TypeDefinitions:Tapi_DirectiveValue;
        }
        leaf costOptimization {
            type TapiModule-TypeDefinitions:Tapi_DirectiveValue;
        }
        leaf linkUtilization {
            type TapiModule-TypeDefinitions:Tapi_DirectiveValue;
        }
        leaf resourceSharing {
            type TapiModule-TypeDefinitions:Tapi_DirectiveValue;
        }
    }
}
