module TapiTopologyPacs {


  namespace "urn:onf:tapi:pacs:yang";
  prefix TapiPacs;
  
  import TapiDataTypes { prefix TapiDt; }

  organization "ONF T-API Group";

  contact "mailto:info@opennetworking.org";

  description
    "This module contains a collection of YANG Topology PACs. It is part of the T-API
     specification.
     Authors List:
     Ricard Vilalta (CTTC)
     Victor López (Telefónica)
     (T-API Team)";
   
  revision 2015-09-11 {
    description
      "First draft for Transport API Topology PACs";
  }
  
  
  // Conditional Pacs associated to TopologicalEntity

  grouping State_Pac {

    leaf operationalState {
      type TapiDt:LifecycleState;
    }
    leaf administrativeState {
      type TapiDt:AdministrativeState;
    }
    leaf lifecycleState {
      type TapiDt:LifecycleState;
    }
    
  }

  grouping RiskParameter_Pac {
    
    list riskCharacteristicList {
       key "riskCharacteristicName";
       uses TapiDt:RiskCharacteristic;
    }
  }

  grouping TransferCost_Pac {
    list costCharacteristicList {
      key "costName";
      uses TapiDt:CostCharacteristics;
      min-elements "1";

      }
  }

  grouping TransferTiming_Pac {
    
    leaf fixedLatencyCharacteristic {
      type string;
      mandatory true;
    }
    leaf jitterCharacteristic {
      type string;
    }
    leaf wanderCharacteristic {
      type string;
    }
    list queuingLatencyList {
      key "trafficProperty";
      uses TapiDt:QueuingLatency;
    }
  }

  grouping TransferIntegrity_Pac {
    
    leaf errorCharacteristic {
      type string;
    }
    leaf lossCharacteristic {
      type string;
    }
    leaf repeatDeliveryCharacteristic {
      type string;
    }
    leaf deliveryOrderCharacteristic {
      type string;
    }
    leaf unavailableTimeCharacteristic {
      type string;
      mandatory true;
    }
    leaf serverIntegrityProcessCharacteristic {
      type string;
    }
  }

  grouping TransferCapacity_Pac {
    
    container totalPotentialCapacity {
      uses TapiDt:Capacity;
    }
    container availableCapacity {
      uses TapiDt:Capacity;
    }
    list capacityAssignedToUserView {
      key "totalSize";
      uses TapiDt:Capacity;
    }
    leaf capacityInteractionAlgorithm {
      type string;
    }
  }

  grouping Validation_Pac {

    list validationMechanismList {
      key "validationMechanism";
      uses TapiDt:ValidationMechanism;
      min-elements "1";
    }
  }

  grouping LayerProtocolTransition_Pac {

    
    list transitionedLayerProtocolList {
      key "transitionedLayerProtocol";
      leaf transitionedLayerProtocol{
        type TapiDt:LayerProtocolName;
      }
    }

    leaf-list _ltpRefList {
      type leafref {
        path "/Tapi:Context/Tapi:topologyList/Tapi:node/Tapi:edgeLtpList/Tapi:uuid"; // Not clear path
      }
    }
  }    
  
  
}
