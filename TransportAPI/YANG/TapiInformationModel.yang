module TapiInformationModel {


  namespace "urn:onf:tapi:im:yang";
  prefix Tapi;
  
  //import ietf-inet-types { prefix inet; }

  import TapiDataTypes { prefix TapiDt; }

  organization "ONF T-API Group";

  contact "mailto:info@opennetworking.org";

  description
    "This module contains a collection of YANG definitions for
     Information Model. It is part of the T-API
     specification.
     Authors List:
     Ricard Vilalta (CTTC)
     Victor López (Telefónica)
     (T-API Team)";
   
  revision 2015-09-11 {
    description
      "First draft for Transport API Connectivity Service";
  }
 
  /*****************************************************************
  * Groupings
  *****************************************************************/

  // Conditional Pacs associated to TopologicalEntity

  grouping State_Pac {

    leaf operationalState {
      type TapiDt:LifecycleState;
    }
    leaf administrativeState {
      type TapiDt:AdministrativeState;
    }
    leaf lifecycleState {
      type TapiDt:LifecycleState;
    }
    
  }

  grouping RiskParameter_Pac {
    
    list riskCharacteristic {
       key "riskCharacteristicName";
       uses TapiDt:RiskCharacteristic;
    }
  }

  grouping TransferCost_Pac {
    list costCharacteristic {
      key "costName";
      uses TapiDt:CostCharacteristics;
      min-elements "1";

      }
  }

  grouping TransferTiming_Pac {
    
    leaf fixedLatencyCharacteristic {
      type string;
      mandatory true;
    }
    leaf jitterCharacteristic {
      type string;
    }
    leaf wanderCharacteristic {
      type string;
    }
    list queuingLatency {
      key "trafficProperty";
      uses TapiDt:QueuingLatency;
    }
  }

  grouping TransferIntegrity_Pac {
    
    leaf errorCharacteristic {
      type string;
    }
    leaf lossCharacteristic {
      type string;
    }
    leaf repeatDeliveryCharacteristic {
      type string;
    }
    leaf deliveryOrderCharacteristic {
      type string;
    }
    leaf unavailableTimeCharacteristic {
      type string;
      mandatory true;
    }
    leaf serverIntegrityProcessCharacteristic {
      type string;
    }
  }

  grouping TransferCapacity_Pac {
    
    container totalPotentialCapacity {
      uses TapiDt:Capacity;
    }
    container availableCapacity {
      uses TapiDt:Capacity;
    }
    list capacityAssignedToUserView {
      key "totalSize";
      uses TapiDt:Capacity;
    }
    leaf capacityInteractionAlgorithm {
      type string;
    }
  }

  grouping Validation_Pac {

    list validationMechanism {
      key "validationMechanism";
      uses TapiDt:ValidationMechanism;
      min-elements "1";
    }
  }

  grouping LayerProtocolTransition_Pac {

    
    list transitionedLayerProtocol {
      key "transitionedLayerProtocol";
      leaf transitionedLayerProtocol{
        type TapiDt:LayerProtocolName;
      }
    }

    leaf-list nodeEdgePoint {
      type leafref {
        path "/Tapi:Context/Tapi:topology/Tapi:node/Tapi:nodeEdgePoint/Tapi:uuid";
      }
    }
  }    
  
  grouping NodeEdgePoint {
    description
    "Node-Edge-Point - represents the node-facing aspect of the edge-port functions for accessing the 
    forwarding capabilities provided by the Node. 
    Node-Edge-Point provides an encapsulation of addressing, mapping, termination, adaptation and OAM 
    functions of one or more transport layers (including circuit and packet forms) performed at the entry/
    exit points of Node. ";

    leaf uuid{
    	type TapiDt:UniversalId;
    }
    
    
    list layerProtocol{ 
      key "layerProtocol";
      uses TapiDt:LayerProtocol;
    }
    
    leaf operationalState {
      type TapiDt:OperationalState;
    }
	
    leaf physicalPortReference {
      type string;
    }
	  
  }
  
  grouping LinkEnd {
    description
    "The association of the Link to LTPs is made via LinkEnd.
    The LinkEnd object class models the access to the Link function. 
    The traffic forwarding between the associated LinkEnds of the Link depends upon the type of Link.  
    In cases where there is resilience the LinkEnd may convey the resilience role of the access to the Link. 
    The Link can be considered as a component and the LinkEnd as a Port on that component";
    
    
    leaf uuid{
    	type TapiDt:UniversalId;
    }
    
    leaf-list nodeEdgePoint {
      type leafref {
        path "/Tapi:Context/Tapi:topology/Tapi:node/Tapi:nodeEdgePoint/Tapi:uuid";
      }
      max-elements "1";
      min-elements "1";      
    }
    
    leaf role {
      type TapiDt:EndRole;
    }
    
    leaf direction {
      type TapiDt:EndDirection;
    }
    
    list localId {
      key "valueName";
      uses TapiDt:NameAndValue;
      min-elements "1";
    }
    
  }
    
  grouping Node {
    description
    "Representation of the opaque forwarding-aspects of the Forwarding-Domain (FD) 
    Node describes the edge ports of the FD (Node-Edge-Point) and the forwarding capabilities between 
    those edge ports.";

    leaf uuid{
    	type TapiDt:UniversalId; // Missing in Tapi UML
    }

    leaf-list encapTopology {
      type leafref {
        path "/Tapi:Context/Tapi:topology/Tapi:uuid";
      }
      max-elements "1";
    }

    list nodeEdgePoint { 
      key "uuid";
      uses NodeEdgePoint;     
    }
    
    list name {
      key "valueName";
      uses TapiDt:NameAndValue;
      min-elements "1";
    }
    
    list label {
      key "valueName";
      uses TapiDt:NameAndValue;
    }
    
    list extension {
      key "valueName";
      uses TapiDt:NameAndValue;
    }    
    
    list layerProtocolName {
      key "layerProtocolName";
      leaf layerProtocolName {
        type TapiDt:LayerProtocolName;
      }
      min-elements "1";
    }
    
    leaf-list connection {
        type leafref {
            path "/Tapi:ConnectivityService/Tapi:connection/Tapi:uuid";
        }
    }

    container _state_Pac {
      presence "<condition for State_Pac attributes>";
      uses State_Pac;
    }
    
    container _riskParameter_Pac {
      presence "<condition for RiskParameter_Pac attributes>";
      uses RiskParameter_Pac;
    }
    
    container _transferCost_Pac {
      presence "<condition for TransferCost_Pac attributes>";
      uses TransferCost_Pac;
    }
    
    container _transferTiming_Pac {
      presence "<condition for TransferTiming_Pac attributes>";
      uses TransferTiming_Pac;
    }
    
    container _transferCapacity_Pac {
      presence "<condition for TransferCapacity_Pac attributes>";
      uses TransferCapacity_Pac;
    }
    
    container _transferIntegrity_Pac {
      presence "<condition for TransferIntegrity_Pac attributes>";
      uses TransferIntegrity_Pac;
    }
    
    container _validation_Pac {
      presence "<condition for Validation_Pac attributes>";    
      uses Validation_Pac;
    }
    
    container _layerTransition_Pac {
      presence "<condition for LayerProtocolTransition_Pac attributes>";
      uses LayerProtocolTransition_Pac;
    }
    
  }

  grouping Link {
    description
    "Representation of the effective adjacency between two or more associated Nodes in a Topology. 
    Link is terminated by Node-Edge-Points of the associated Nodes. The Node-Edge-Points have a specific    
    role with respect to the Link";
    
    leaf uuid{
    	type TapiDt:UniversalId;
    }

    list linkEnd {
      key "uuid";
      uses LinkEnd;
    }
  
    leaf-list node{
      type leafref {
        path "/Tapi:Context/Tapi:topology/Tapi:node/Tapi:uuid";
      }
    }
  
  
   list name {
      key "valueName";
      uses TapiDt:NameAndValue;
      min-elements "1";
    }
    
    list label {
      key "valueName";
      uses TapiDt:NameAndValue;
    }
    
    list extension {
      key "valueName";
      uses TapiDt:NameAndValue;
    }    
    
    list layerProtocolName {
      key "layerProtocolName";
      leaf layerProtocolName {
        type TapiDt:LayerProtocolName;
      }
      min-elements "1";
    }
    
    leaf linkDirection {
      type TapiDt:ForwardingDirection;
    }
    
    container _state_Pac {
      presence "<condition for State_Pac attributes>";
      uses State_Pac;
    }
    
    container _riskParameter_Pac {
      presence "<condition for RiskParameter_Pac attributes>";
      uses RiskParameter_Pac;
    }
    
    container _transferCost_Pac {
      presence "<condition for TransferCost_Pac attributes>";
      uses TransferCost_Pac;
    }
    
    container _transferTiming_Pac {
      presence "<condition for TransferTiming_Pac attributes>";
      uses TransferTiming_Pac;
    }
    
    container _transferCapacity_Pac {
      presence "<condition for TransferCapacity_Pac attributes>";
      uses TransferCapacity_Pac;
    }
    
    container _transferIntegrity_Pac {
      presence "<condition for TransferIntegrity_Pac attributes>";
      uses TransferIntegrity_Pac;
    }
    
    container _validation_Pac {
      presence "<condition for Validation_Pac attributes>";    
      uses Validation_Pac;
    }
    
    container _layerTransition_Pac {
      presence "<condition for LayerProtocolTransition_Pac attributes>";
      uses LayerProtocolTransition_Pac;
    }
    
  }
  
  grouping Topology {
    description
    "Representation of the transparent topological-aspects of a Forwarding-Domain (FD).
    Topology describes the underlying topological network of Nodes and Links that enable the forwarding 
    function provided by the FD.";

    leaf uuid{
    	type TapiDt:UniversalId;
    }
    
    list node {
      key "uuid";
      uses Node;
    }
    
    list link {
      key "uuid";
      uses Link;
    }
    
    list name {
      key "valueName";
      uses TapiDt:NameAndValue;
      min-elements "1";
    }
    
    list label {
      key "valueName";
      uses TapiDt:NameAndValue;
    }
    
    list extension {
      key "valueName";
      uses TapiDt:NameAndValue;
    }    
    
    list layerProtocolName {
      key "layerProtocolName";
      leaf layerProtocolName {
        type TapiDt:LayerProtocolName;
      }
    }
  }
  
  grouping ServiceEndPoint {
    description
    "Service-End-Point  - represents the outward-facing aspect of the edge-port functions for accessing the 
    forwarding capabilities provided by Node.
    Service-End-Point provides a limited, simplified view of interest to external clients (e.g. client 
    addressing, capacity, resource availability, etc), that enable the clients to make a connectivity 
    service request without the need to understand the provider network internals.
    Service-End-Point have a mapping relationship (one-to-one, one-to-many, many-to-many) to Node-Edge-
    Points";
  
    leaf uuid{
    	type TapiDt:UniversalId;
    }
    
    list layerProtocol {
      key "layerProtocol";
      uses TapiDt:LayerProtocol;
      min-elements "1";
    }

    leaf operationalState {
      type TapiDt:OperationalState;
    }
    
    leaf-list mappedNodeEp {
      type leafref {
        path "/Tapi:Context/Tapi:topology/Tapi:node/Tapi:nodeEdgePoint/Tapi:uuid";
      }
    }
    
  }
  
  grouping ConnectionEndPoint {
    description
    "Connection-End-Point - represents the ingress/egress port functions  for accessing to the forwarding   
    function provided by the Connection.
    Connection-End-Point have client-server relationship with Node-Edge-Points";
  
    leaf uuid{
    	type TapiDt:UniversalId;
    }

    list layerProtocol{
      key "layerProtocol";
      uses TapiDt:LayerProtocol;
      min-elements "1";
    }
    
    leaf operationalState {
      type TapiDt:OperationalState;
    }
    
    list clientNodeEp {
        key "uuid";
        uses NodeEdgePoint;
    }
    
    container serverNodeEp {
        uses NodeEdgePoint;
    }    
    
  }

  grouping ConnectionPort {
    description
    "The association of the FC to LTPs is made via EndPoints.
    The EndPoint (EP) object class models the access to the FC function. 
    The traffic forwarding between the associated EPs of the FC depends upon the type of FC and may be associated 
    with  FcSwitch object instances.  
    In cases where there is resilience the EndPoint may convey the resilience role of the access to the FC. 
    It can represent a protected (resilient/reliable) point or a protecting (unreliable working or protection) point.
    The EP replaces the Protection Unit of a traditional protection model. 
    The ForwadingConstruct can be considered as a component and the EndPoint as a Port on that component";

    leaf uuid{
    	type TapiDt:UniversalId;
    }
    
    container connectionEndPoint { // Differs
      uses ConnectionEndPoint;
    }

    leaf role {
      type TapiDt:EndRole;
    }
    
    leaf direction {
      type TapiDt:EndDirection;
    }
    
  }

  grouping ServicePort {
  
    leaf uuid{
    	type TapiDt:UniversalId; 
    }
  
    leaf serviceEndPoint {
        type leafref {
          path "/Tapi:Context/Tapi:serviceEndPoint/Tapi:uuid";
        }
    }    

    leaf role {
      type TapiDt:EndRole;
    }
    
    leaf direction {
      type TapiDt:EndDirection;
    }
  
  }

  grouping Path {
    description
    "Path - represents the route of a Connection through the lower-level Nodes in the underlying Topology
    Path is described as a list of references to the lower-level Connections.";


    leaf uuid{
    	type TapiDt:UniversalId; // Differs
    }

    leaf-list lowerLevelConnection{
      type leafref {
        path "/Tapi:ConnectivityService/Tapi:connection/Tapi:uuid";
      }
      min-elements "1";
    }
  }
  
  grouping Connection {
    description
    "Connection - represents an enabled (provisioned) potential for forwarding (including all circuit and 
    packet forms) between two or more Node-Edge-Points of a Node. 
    Connection is a container for provisioned connectivity that tracks the state of the allocated resources 
    and is distinct from the connectivity Service request.";

    leaf uuid{
    	type TapiDt:UniversalId; // Differs
    }

    list connectionPort { 
      key "uuid";
      uses ConnectionPort;
      max-elements "2";
    }

    list path {
      key "uuid";
      uses Path;
    }

    leaf-list node {
      type leafref {
        path "/Tapi:Context/Tapi:topology/Tapi:node/Tapi:uuid";
      }
    }
    
    leaf layerProtocolName {
      type TapiDt:LayerProtocolName;
    } 
    
    container _state_Pac {
      presence "<condition for State_Pac attributes>";
      uses State_Pac;
    }
    
    container _transferCost_Pac {
      presence "<condition for TransferCost_Pac attributes>";
      uses TransferCost_Pac;
    }
    
    container _transferTiming_Pac {
      presence "<condition for TransferTiming_Pac attributes>";
      uses TransferTiming_Pac;
    }
    
    container _transferCapacity_Pac {
      presence "<condition for TransferCapacity_Pac attributes>";
      uses TransferCapacity_Pac;
    }
    
    container _transferIntegrity_Pac {
      presence "<condition for TransferIntegrity_Pac attributes>";
      uses TransferIntegrity_Pac;
    }

  }
  
  grouping ConnectivityService {
    description
    "Connectivity Service - represents an “intent-like” request for connectivity between two or more 
    Service-End-Points.
    Service is a container for connectivity request details and is distinct from Connection that realizes 
    the request
    They refer to different aspects of information exchanged over T-API interface, but within provider they 
    could be modeled by the same instance if there is one-to-one mapping.";

    leaf uuid{
    	type TapiDt:UniversalId; // Differs
    }

    list connection {
        key "uuid";
        uses Connection;
    }
  
    list servicePort { //Differs from UML
      key "uuid";
      uses ServicePort;
      max-elements "2";
    }
    
    leaf layerProtocolName {
      type TapiDt:LayerProtocolName;
    }
    
    container _state_Pac {
      presence "<condition for State_Pac attributes>";
      uses State_Pac;
    }
    
    container _transferCost_Pac {
      presence "<condition for TransferCost_Pac attributes>";
      uses TransferCost_Pac;
    }
    
    container _transferTiming_Pac {
      presence "<condition for TransferTiming_Pac attributes>";
      uses TransferTiming_Pac;
    }
    
    container _transferCapacity_Pac {
      presence "<condition for TransferCapacity_Pac attributes>";
      uses TransferCapacity_Pac;
    }
    
    container _transferIntegrity_Pac {
      presence "<condition for TransferIntegrity_Pac attributes>";
      uses TransferIntegrity_Pac;
    }

  }
  
  grouping Context {
  
    leaf uuid{
    	type TapiDt:UniversalId; // Differs
    }  
    
    list topology { // Differs from UML
      key "uuid";
      uses Topology;
      max-elements "1";
    }

    list serviceEndPoint {
        key "uuid";
        uses ServiceEndPoint;
    }
    
  }
  
  /*****************************************************************
  * Main containers
  *****************************************************************/
 
  list ConnectivityService {
    description
    "The ForwardingConstruct (FC) object class models enabled potential for forwarding between two or more LTPs and like the LTP supports any       
    transport protocol including all circuit and packet forms. 
    At the lowest level of recursion, a FC represents a cross-connection within an NE.";
    
    key "uuid";
    uses ConnectivityService;
  }
  
  list Context {
    description
    "(API) Context  defines the scope of control and naming that a particular T-API provider or its client  
    application has with respect to the information exchanged over the interface.
    This Context is shared between the API provider and its client and determines the makeup of the network 
    resource abstractions over which the API operates.";
    
    key "uuid";
    uses Context;
    
  }
   
}
