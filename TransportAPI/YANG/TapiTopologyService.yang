module TapiTopologyService {

  namespace "urn:onf:Tapi:TopologyService:yang";
  prefix TapiTopologyService;
  
  import TapiInformationModel { prefix Tapi; }
  import TapiDataTypes { prefix TapiDt; }
  
  organization "ONF T-API Group";

  contact "mailto:info@opennetworking.org";

  description
    "This module contains a collection of YANG definitions for
     Topology Service. It is part of the T-API
     specification.
     Authors List:
     Ricard Vilalta (CTTC)
     Victor López (Telefónica)
     (T-API Team)";
   
  revision 2015-09-11 {
    description
      "First draft for Transport API Topology Service";
  }
 
 
  
  /*****************************************************************
  * RPC definitions
  *****************************************************************/
    
  rpc getTopologyDetails {
    input {
      description "topology id";
        leaf uuid{
          type TapiDt:UniversalId;
        }
    }
  
    output {
      container topology {
          uses Tapi:Topology;
      }
    }
  }
  
  rpc getLinkDetails {
    input {
      description "link id";
        leaf uuid{
          type TapiDt:UniversalId;
        }
    }
    output {
      container link{
        uses Tapi:Link;
      }
    }
  }
  
  rpc getNodeDetails {
    input {
      description "node id";
        leaf uuid{
          type TapiDt:UniversalId;
        }
    }
    output {
      container node{
        uses Tapi:Node;
      }
    }
  }
  
  rpc getNodeEdgePointDetails {
    input {
      description "node edge point id";
        leaf uuid{
          type TapiDt:UniversalId;
        }
    }
    output {
      container nodeEdgePoint{
        uses Tapi:NodeEdgePoint;
      }
    }
  }  
}
