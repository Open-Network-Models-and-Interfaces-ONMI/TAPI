module Tapi-Interfaces-PathComputationService {
    namespace "uri:onf:Tapi-Interfaces-PathComputationService";
    prefix Tapi-Interfaces-PathComputationService;
    import Tapi-ObjectClasses {
        prefix Tapi-ObjectClasses;
    }
    revision 2016-05-22{}
    rpc computeP2PPath {
        input {
            list servicePort {
                ordered-by system;
                uses Tapi-ObjectClasses:ConnectivityServicePort;
                max-elements 2;
                min-elements 2;
            }
            container routingConstraint {
                uses Tapi-ObjectClasses:ConnectivityConstraint;
            }
            container objectiveFunction {
                uses Tapi-ObjectClasses:PathObjectiveFunction;
            }
        }
        output {
            list path {
                ordered-by system;
                uses Tapi-ObjectClasses:Path;
                min-elements 1;
            }
        }
    }
    rpc optimizeP2PPath {
        input {
            leaf pathIdOrName {
                type string;
            }
            container routingConstraint {
                uses Tapi-ObjectClasses:ConnectivityConstraint;
            }
            container optimizationConstraint {
                uses Tapi-ObjectClasses:PathOptimizationConstraint;
            }
            container objectiveFunction {
                uses Tapi-ObjectClasses:PathObjectiveFunction;
            }
        }
        output {
            list path {
                ordered-by system;
                uses Tapi-ObjectClasses:Path;
                min-elements 1;
            }
        }
    }
}
