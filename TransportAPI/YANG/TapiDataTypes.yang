module TapiDataTypes {


  namespace "urn:onf:tapi:dt:yang";
  prefix TapiDt;
  

  organization "ONF T-API Group";

  contact "mailto:info@opennetworking.org";

  description
    "This module contains a collection of YANG Data Types. It is part of the T-API
     specification.
     Authors List:
     Ricard Vilalta (CTTC)
     Victor López (Telefónica)
     (T-API Team)";
   
  revision 2015-09-11 {
    description
      "First draft for Transport API Data Types";
  }

  typedef LifecycleState {
    type enumeration {
      enum PLANNED;
      enum POTENTIAL;
      enum INSTALLED;
      enum PENDING_REMOVAL;
    }
  }

  typedef TerminationDirection {
    type enumeration {
      enum BIDIRECTIONAL;
      enum SINK;
      enum SOURCE;
      enum UNDEFINED_OR_UNKNOWN;
    }
  }
  
  typedef EndDirection {
    type enumeration {
      enum BIDIRECTIONAL;
      enum INPUT;
      enum OUTPUT;
      enum UNDEFINED_OR_UNKNOWN;
    }
  }
  
  typedef ForwardingDirection {
    type enumeration {
      enum BIDIRECTIONAL;
      enum UNIDIRECTIONAL;
      enum UNDEFINED_OR_UNKNOWN;
    }
  }
  
  typedef OperationalState {
    type enumeration {
      enum DISABLED;
      enum ENABLED;
    }
  }
  
  typedef AdministrativeState {
    type enumeration {
      enum LOCKED;
      enum UNLOCKED;
    }
  }
  
  typedef LayerProtocolName {
    type enumeration {
      enum ETH;
      enum MPLS-TP;
      enum ODU;
      enum OCH;
    }
  }
  
  typedef EndRole {
    type enumeration {
      enum SYMMETRIC;
      enum ROOT;
      enum LEAF;
    }
  }
  typedef UniversalId {
      type string;
  }
  
  grouping LayerProtocol {
    leaf layerProtocol {
      type string;
    }
  }
  
  grouping NameAndValue {
    
    leaf value {
      type string;
    }
    
    leaf valueName {
      type string;
    }
  
  }  
  
  /** 
   * PAC groupings
   */
  
  grouping Capacity {
    leaf totalSize {
      type string;
      mandatory true;
    }
    leaf numberOfClientInstances {
      type string;
    }
    leaf maximumClientSize {
      type string;
    }
    leaf numberingRange {
      type string;
    }
  }
  
  grouping CostCharacteristics {
    leaf costName {
      type string;
      mandatory true;
    }
    leaf costValue {
      type string;
      mandatory true;
    }
    leaf costAlgorithm {
      type string; // Undefined in the model
    }
  }
  
  grouping RiskCharacteristic {
    leaf riskCharacteristicName {
      type string;
      mandatory true;
    }
    list riskIdentifierList {
      key "ristIdentifier";
      leaf ristIdentifier{
        type string;
      }
      min-elements "1";
    }
  }
  
  grouping ValidationMechanism {
     leaf validationMechanism {
        type string;
        mandatory true;
     }
     leaf layerProtocolAdjacencyValidated {
        type string;
        mandatory true;
     }
     leaf validationRobustness {
        type string;
        mandatory true;
     }
  }
  
  grouping QueuingLatency {
  
    leaf trafficProperty {
      type string;
      mandatory true;
    }
    leaf latencyForTrafficWithProperty {
      type string;
      mandatory true;
    }
    
  }
            
}
