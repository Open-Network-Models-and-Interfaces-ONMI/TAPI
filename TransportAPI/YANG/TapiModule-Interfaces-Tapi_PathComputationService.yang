module TapiModule-Interfaces-Tapi_PathComputationService {
    namespace "uri:onf:TapiModule-Interfaces-Tapi_PathComputationService";
    prefix TapiModule-Interfaces-Tapi_PathComputationService;
    import TapiModule-ObjectClasses {
        prefix TapiModule-ObjectClasses;
    }
    revision 2016-03-15{}
    rpc computeP2PPath {
        input {
            list servicePort {
                ordered-by system;
                uses TapiModule-ObjectClasses:G_Tapi_ServicePort;
                max-elements 2;
                min-elements 2;
            }
            container routingConstraint {
                uses TapiModule-ObjectClasses:G_Tapi_ConnectivityConstraint;
            }
            container objectiveFunction {
                uses TapiModule-ObjectClasses:G_Tapi_PathObjectiveFunction;
            }
        }
        output {
            list path {
                ordered-by system;
                uses TapiModule-ObjectClasses:G_Tapi_Path;
                min-elements 1;
            }
        }
    }
    rpc optimizeP2PPath {
        input {
            leaf pathIdOrName {
                type string;
            }
            container routingConstraint {
                uses TapiModule-ObjectClasses:G_Tapi_ConnectivityConstraint;
            }
            container optimizationConstraint {
                uses TapiModule-ObjectClasses:G_Tapi_PathOptimizationConstraint;
            }
            container objectiveFunction {
                uses TapiModule-ObjectClasses:G_Tapi_PathObjectiveFunction;
            }
        }
        output {
            list path {
                ordered-by system;
                uses TapiModule-ObjectClasses:G_Tapi_Path;
                min-elements 1;
            }
        }
    }
}
