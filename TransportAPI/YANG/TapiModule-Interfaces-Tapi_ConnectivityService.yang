module TapiModule-Interfaces-Tapi_ConnectivityService {
    namespace "uri:onf:TapiModule-Interfaces-Tapi_ConnectivityService";
    prefix TapiModule-Interfaces-Tapi_ConnectivityService;
    import TapiModule-ObjectClasses {
        prefix TapiModule-ObjectClasses;
    }
    revision 2016-03-15{}
    rpc getConnectionDetails {
        input {
            leaf serviceIdOrName {
                type string;
            }
            leaf connectionIdOrName {
                type string;
            }
        }
        output {
            container connection {
                uses TapiModule-ObjectClasses:G_Tapi_Connection;
            }
        }
    }
    rpc getConnectivityServiceList {
        output {
            list serviceList {
                ordered-by system;
                uses TapiModule-ObjectClasses:G_Tapi_ConnectivityService;
            }
        }
    }
    rpc getConnectionEndPointDetails {
        input {
            leaf serviceIdOrName {
                type string;
            }
            leaf connectionIdOrName {
                type string;
            }
            leaf connEPIdOrName {
                type string;
            }
        }
        output {
            container connEP {
                uses TapiModule-ObjectClasses:G_Tapi_ConnectionEndPoint;
            }
        }
    }
    rpc getServiceEndPointDetails {
        input {
            leaf serviceEPIdOrName {
                type string;
            }
        }
        output {
            container serviceEP {
                uses TapiModule-ObjectClasses:G_Tapi_ServiceEndPoint;
            }
        }
    }
    rpc getConnectivityServiceDetails {
        input {
            leaf serviceIdOrName {
                type string;
            }
        }
        output {
            container service {
                uses TapiModule-ObjectClasses:G_Tapi_ConnectivityService;
            }
        }
    }
    rpc getServiceEndPointList {
        output {
            list serviceEPList {
                ordered-by system;
                uses TapiModule-ObjectClasses:G_Tapi_ServiceEndPoint;
            }
        }
    }
    rpc createConnectivityService {
        input {
            list servicePort {
                ordered-by system;
                uses TapiModule-ObjectClasses:G_Tapi_ServicePort;
                min-elements 2;
            }
            container connConstraint {
                uses TapiModule-ObjectClasses:G_Tapi_ConnectivityConstraint;
            }
            container connSchedule {
                uses TapiModule-ObjectClasses:G_Tapi_ScheduleInfo;
            }
        }
        output {
            container connService {
                uses TapiModule-ObjectClasses:G_Tapi_ConnectivityService;
            }
        }
    }
    rpc updateConnectivityService {
        input {
            leaf serviceIdOrName {
                type string;
            }
            container connConstraint {
                uses TapiModule-ObjectClasses:G_Tapi_ConnectivityConstraint;
            }
            container connSchedule {
                uses TapiModule-ObjectClasses:G_Tapi_ScheduleInfo;
            }
        }
        output {
            container connService {
                uses TapiModule-ObjectClasses:G_Tapi_ConnectivityService;
            }
        }
    }
    rpc deleteConnectivityService {
        input {
            leaf serviceIdOrName {
                type string;
            }
        }
        output {
            container connService {
                uses TapiModule-ObjectClasses:G_Tapi_ConnectivityService;
            }
        }
    }
}
