module TapiModule-Interfaces-Tapi_TopologyService {
    namespace "uri:onf:TapiModule-Interfaces-Tapi_TopologyService";
    prefix TapiModule-Interfaces-Tapi_TopologyService;
    import TapiModule-ObjectClasses {
        prefix TapiModule-ObjectClasses;
    }
    revision 2016-03-15{}
    rpc getTopologyDetails {
        input {
            leaf topologyIdOrName {
                type string;
            }
        }
        output {
            container topology {
                uses TapiModule-ObjectClasses:G_Tapi_Topology;
            }
        }
    }
    rpc getNodeDetails {
        input {
            leaf topologyIdOrName {
                type string;
            }
            leaf nodeIdOrName {
                type string;
            }
        }
        output {
            container node {
                uses TapiModule-ObjectClasses:G_Tapi_Node;
            }
        }
    }
    rpc getNodeEdgePointDetails {
        input {
            leaf topologyIdOrName {
                type string;
            }
            leaf nodeIdOrName {
                type string;
            }
            leaf epIdOrName {
                type string;
            }
        }
        output {
            container nodeEdgePoint {
                uses TapiModule-ObjectClasses:G_Tapi_NodeEdgePoint;
            }
        }
    }
    rpc getLinkDetails {
        input {
            leaf topologyIdOrName {
                type string;
            }
            leaf linkIdOrName {
                type string;
            }
        }
        output {
            container link {
                uses TapiModule-ObjectClasses:G_Tapi_Link;
            }
        }
    }
}
